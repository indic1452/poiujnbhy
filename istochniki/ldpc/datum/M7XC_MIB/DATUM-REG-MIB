-- ********************************************************************
--
--  Datum Systems, Inc.
--  7211 E. Southern Ave, Suite 102
--  Mesa, 85209-2793
--  (480) 558-5500
--
--
--  This module provides authoritative definitions for Datum Systems'
--  enterprise-specific internal MIB.
--
--  This module will be extended, as required.
--
--  Generic naming is used to insure the customer does not access
--  the attributes of this MIB, unless instructed by technical
--  support.
--
--  Datum Systems reserves the right to make changes in
--  specification and other information contained in this document
--  without prior notice.  The reader should consult Datum Systems
--  to determine whether any such changes have been made.
--
--  In no event shall Datum Systems be liable for any incidental,
--  indirect, special, or consequential damages whatsoever (including
--  but not limited to lost profits) arising out of or related to this
--  document or the information contained in it, even if Datum Systems
--  has been advised of, known, or should have known, the possibility
--  of such damages.
--
--  Datum Systems grants vendors, end-users, and other interested
--  parties a non-exclusive license to use this Specification in
--  connection with the management of Datum Systems' products.
--
--
--  Copyright June 2020-2023 Datum Systems, Inc.
--
-- ********************************************************************

--
-- Datum Systems, Inc. Global Reg Module
--

DATUM-REG-MIB DEFINITIONS ::= BEGIN

IMPORTS
        MODULE-IDENTITY, OBJECT-IDENTITY,
        enterprises
            FROM SNMPv2-SMI;

--
-- The module identification
--
datumGlobalRegModule MODULE-IDENTITY
        LAST-UPDATED "202108161748Z"  -- August 16, 2021, 17:48
        ORGANIZATION "Datum Systems, Inc."
        CONTACT-INFO
            "Contact: Customer Support Group

              Postal: Datum Systems, Inc.
                      Customer Support Group
                      7211 E. Southern Ave, Suite 102
                      Mesa, AZ 85209-2793
                      US
                 Tel: +1 (480) 558-5500
                 Web: http://www.datumsystems.com/
               email: Support@DatumSystems.com"
        DESCRIPTION  "The Datum Systems, Inc central registration module"

        REVISION     "202108161748Z"  -- August 16, 2021, 17:48
        DESCRIPTION  "Full Auto Update Version."

    ::= { datumModules 1 }

--
-- the root of the sub-tree for Datum Systems, Inc.
--
datumSystems        OBJECT IDENTIFIER ::= { enterprises 31968 }

--
-- sub-tree for registrations, which includes modules
--
datumReg            OBJECT IDENTIFIER ::= { datumSystems 1 }
datumModules        OBJECT IDENTIFIER ::= { datumReg 1 }

--
-- sub-tree for company-wide objects and events
--
datumGeneric        OBJECT IDENTIFIER ::= { datumSystems 2 }
--
-- sub-tree for product-specific objects and events
--
datumProducts       OBJECT IDENTIFIER ::= { datumSystems 3 }
--
-- sub-tree for modem products-specific objects and events
--
modems       OBJECT IDENTIFIER ::= { datumProducts 1 }

--
-- sub-tree for agent profiles
--
datumCaps           OBJECT IDENTIFIER ::= { datumSystems 4 }
--
-- sub-tree for requirement specifications
--
datumReqs           OBJECT IDENTIFIER ::= { datumSystems 5 }
--
-- sub-tree for experiments
--
datumExpr           OBJECT IDENTIFIER ::= { datumSystems 6 }

--
-- Product lines
--
satelliteModemsReg  OBJECT IDENTIFIER ::= { datumReg 2 }

--
--  Products
--  the registrations for the actual hardware
--
m4900ModemReg   OBJECT-IDENTITY
        STATUS       current
        DESCRIPTION "The M4900/M5 Class Satellite Modem"
    ::= { satelliteModemsReg 1 }

m500ModemReg    OBJECT-IDENTITY
        STATUS       current
        DESCRIPTION "The M500 Class Satellite Modem"
    ::= { satelliteModemsReg 2 }

m7ModemReg      OBJECT-IDENTITY
        STATUS       current
        DESCRIPTION "The M7 Class Satellite Modem"
    ::= { satelliteModemsReg 3 }

m7xcModemReg    OBJECT-IDENTITY
        STATUS       current
        DESCRIPTION "The M7XC Class Satellite Modem"
    ::= { satelliteModemsReg 4 }

t7xcModemReg    OBJECT-IDENTITY
        STATUS       current
        DESCRIPTION "The T7XC Class Troposcatter/Satellite Modem"
    ::= { satelliteModemsReg 5 }

END
