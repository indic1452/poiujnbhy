-- ********************************************************************
--
--  Datum Systems, Inc.
--  7211 E. Southern Ave, Suite 102
--  Mesa, 85209-2793
--  (480) 558-5500
--
--
--  This module provides authoritative definitions for Datum Systems'
--  enterprise-specific internal MIB.
--
--  This module will be extended, as required.
--
--  Generic naming is used to insure the customer does not access
--  the attributes of this MIB, unless instructed by technical
--  support.
--
--  Datum Systems reserves the right to make changes in
--  specification and other information contained in this document
--  without prior notice.  The reader should consult Datum Systems
--  to determine whether any such changes have been made.
--
--  In no event shall Datum Systems be liable for any incidental,
--  indirect, special, or consequential damages what so ever (including
--  but not limited to lost profits) arising out of or related to this
--  document or the information contained in it, even if Datum Systems
--  has been advised of, known, or should have known, the possibility
--  of such damages.
--
--  Datum Systems grants vendors, end-users, and other interested
--  parties a non-exclusive license to use this Specification in
--  connection with the management of Datum Systems' products.
--
--
--  Copyright June 2020-2025 Datum Systems, Inc.
--
-- ********************************************************************

--
-- Datum Systems, Inc. M7XC Class Modem MIB Module
-- Firmware Build: 3.0.8
--

DATUM-M7XC-MODEM-MIB DEFINITIONS ::= BEGIN

IMPORTS
--      SMIv1 translations may require Gauge
--      Gauge
--          FROM RFC1155-SMI
        MODULE-IDENTITY, OBJECT-TYPE, Integer32, Unsigned32, IpAddress
            FROM SNMPv2-SMI
        DisplayString, PhysAddress, DateAndTime
            FROM SNMPv2-TC
        MODULE-COMPLIANCE, OBJECT-GROUP
            FROM SNMPv2-CONF
        datumModules, modems
            FROM DATUM-REG-MIB;

--
-- The module identification
--
m7xcModemMibModule MODULE-IDENTITY
        LAST-UPDATED "202512092023Z"  -- December 9, 2025, 08:23
        ORGANIZATION "Datum Systems, Inc."
        CONTACT-INFO
            "Contact: Customer Support Group

              Postal: Datum Systems, Inc.
                      Customer Support Group
                      7211 E. Southern Ave, Suite 102
                      Mesa, AZ 85209-2793
                      US
                 Tel: +1 (480) 558-5500
                 Web: http://www.datumsystems.com/
               email: Support@DatumSystems.com"
        DESCRIPTION  "The Datum Systems, Inc. M7XC Satellite Modem MIB."

        REVISION     "202512092023Z"  -- December 9, 2025, 08:23
        DESCRIPTION  "Full Auto Update Version."

    ::= { datumModules 6 }

-- Definition of MIB's root nodes
--
-- root for items in the modem MIB module
--
m7xcModem				OBJECT IDENTIFIER ::= { modems 4 }

--
-- sub-tree for objects, and for each functional area
--

m7xcModemObjs			OBJECT IDENTIFIER ::= { m7xcModem 1 }
m7xcModemConformance	OBJECT IDENTIFIER ::= { m7xcModem 3 }

unitCompliance MODULE-COMPLIANCE
    STATUS      current
    DESCRIPTION "Specification requirement"
    MODULE
    MANDATORY-GROUPS { unitInfoGroup }
--  MANDATORY-GROUPS { unitInfoGroup, unitNotificationGroup }
    ::= { m7xcModemConformance 1 }

-- Textual Conventions


-- --------------------------------------------------
unitStatusItems			OBJECT IDENTIFIER ::= { m7xcModemObjs 1 }
unitConfigItems			OBJECT IDENTIFIER ::= { m7xcModemObjs 2 }
rxStatusItems			OBJECT IDENTIFIER ::= { m7xcModemObjs 3 }
rxConfigItems			OBJECT IDENTIFIER ::= { m7xcModemObjs 5 }
txStatusItems			OBJECT IDENTIFIER ::= { m7xcModemObjs 7 }
txConfigItems			OBJECT IDENTIFIER ::= { m7xcModemObjs 9 }
eventLogItems			OBJECT IDENTIFIER ::= { m7xcModemObjs 11 }

unitStatus OBJECT-TYPE
	SYNTAX		INTEGER {
		noAlarmsOrWarnings(0),
		eventPending(1),
		trialFeatureActive(2),
		eventPendingAlarm(3),
		trialExpiresInLessThan7Days(4),
		monitorInputAlarm(5),
		testActive(6),
		firmwarePendingRebootToUse(7),
		mgmtPortAlarm(8),
		dataPortAlarm(9),
		referenceAlarm(10),
		rxAlarm(11),
		txAlarm(12),
		ocxoWarming(13),
		redundancyAlarm(14),
		trialExpiresInLessThan24Hours(15),
		hardwareAlarm(16),
		powerUnderVoltageAlarm(17),
		powerOverVoltageAlarm(18),
		overTemperatureAlarm(19),
		overTemperatureShutdown(20),
		rtcBatteryUnderVoltageAlarm(21),
		rtcBatteryOverVoltageAlarm(22),
		acuAlarm(23),
		redundancyAlarm(24)
	}
	MAX-ACCESS	read-only
	STATUS		current
	DESCRIPTION "Summary Status, where:
			    0) 'No Alarms Or Warnings'
			    1) 'Event Pending'
			    2) 'Trial Feature Active'
			    3) 'EVENT PENDING ALARM'
			    4) 'TRIAL EXPIRES IN < 7 DAYS'
			    5) 'MONITOR INPUT ALARM'
			    6) 'TEST ACTIVE'
			    7) 'FIRMWARE PENDING, REBOOT TO USE'
			    8) 'MGMT PORT ALARM'
			    9) 'DATA PORT ALARM'
			    10) 'REFERENCE ALARM'
			    11) 'Rx ALARM'
			    12) 'Tx ALARM'
			    13) 'OCXO Warming...'
			    14) 'REDUNDANCY ALARM'
			    15) 'TRIAL EXPIRES IN < 24 HOURS'
			    16) 'HARDWARE ALARM'
			    17) 'POWER UNDER VOLTAGE ALARM'
			    18) 'POWER OVER VOLTAGE ALARM'
			    19) 'OVER TEMPERATURE ALARM'
			    20) 'OVER TEMPERATURE SHUTDOWN'
			    21) 'RTC BATTERY UNDER VOLTAGE ALARM'
			    22) 'RTC BATTERY OVER VOLTAGE ALARM'
			    23) 'ACU ALARM'
			    24) 'REDUNDANCY ALARM'
			Oid=1.3.6.1.4.1.31968.3.1.4.1.1.1
			"
	::= { unitStatusItems 1 }

unitBinaryStatus OBJECT-TYPE
	SYNTAX		BITS {
		almTempShutdown(0),
		almOverTemp(1),
		almOverVoltage(2),
		almUnderVoltage(3),
		almHardware(4),
		almDataPort(5),
		almMgmtPort(6),
		almMonitorInput(7),
		almRx(8),
		almTx(9),
		almRef(10),
		almOxcoWarming(11),
		almRedundancy(12),
		almTestActive(13),
		almTrial24Hours(14),
		almTrial7Days(15),
		almLedActive(16),
		relayActive(17),
		trialActive(18),
		eventPending(19),
		firmwarePending(20),
		almRefFallback(21),
		almRtcBatteryOverVoltage(22),
		almRtcBatteryUnderVoltage(23),
		almAcu(24),
		almRedundancy(25)
	}
	MAX-ACCESS	read-only
	STATUS		current
	DESCRIPTION "Binary Status, where:
			    0) 'Alm Temp Shutdown'
			    1) 'Alm Over Temp'
			    2) 'Alm Over Voltage'
			    3) 'Alm Under Voltage'
			    4) 'Alm Hardware'
			    5) 'Alm Data Port'
			    6) 'Alm Mgmt Port'
			    7) 'Alm Monitor Input'
			    8) 'Alm Rx'
			    9) 'Alm Tx'
			    10) 'Alm Ref'
			    11) 'Alm OXCO Warming'
			    12) 'Alm Redundancy'
			    13) 'Alm Test Active'
			    14) 'Alm Trial 24 Hours'
			    15) 'Alm Trial 7 Days'
			    16) 'Alm LED Active'
			    17) 'Relay Active'
			    18) 'Trial Active'
			    19) 'Event Pending'
			    20) 'Firmware Pending'
			    21) 'Alm Ref Fallback'
			    22) 'Alm RTC Battery Over Voltage'
			    23) 'Alm RTC Battery Under Voltage'
			    24) 'Alm ACU'
			    25) 'Alm Redundancy'
			Oid=1.3.6.1.4.1.31968.3.1.4.1.1.2
			"
	::= { unitStatusItems 2 }

powerVoltage OBJECT-TYPE
	SYNTAX		Unsigned32
	UNITS		"0.1 V"
	MAX-ACCESS	read-only
	STATUS		current
	DESCRIPTION "Power Input Voltage
			Oid=1.3.6.1.4.1.31968.3.1.4.1.1.3
			"
	::= { unitStatusItems 3 }

model OBJECT-TYPE
	SYNTAX		DisplayString
	MAX-ACCESS	read-only
	STATUS		current
	DESCRIPTION "Model
			Oid=1.3.6.1.4.1.31968.3.1.4.1.1.4
			"
	::= { unitStatusItems 4 }

sn OBJECT-TYPE
	SYNTAX		Unsigned32
	UNITS		"1"
	MAX-ACCESS	read-only
	STATUS		current
	DESCRIPTION "Serial Number
			Oid=1.3.6.1.4.1.31968.3.1.4.1.1.5
			"
	::= { unitStatusItems 5 }

firmware OBJECT-TYPE
	SYNTAX		DisplayString
	MAX-ACCESS	read-only
	STATUS		current
	DESCRIPTION "Firmware Version
			Oid=1.3.6.1.4.1.31968.3.1.4.1.1.6
			"
	::= { unitStatusItems 6 }

build OBJECT-TYPE
	SYNTAX		DisplayString
	MAX-ACCESS	read-only
	STATUS		current
	DESCRIPTION "Build
			Oid=1.3.6.1.4.1.31968.3.1.4.1.1.7
			"
	::= { unitStatusItems 7 }

trialTime OBJECT-TYPE
	SYNTAX		Unsigned32
	UNITS		"1 s"
	MAX-ACCESS	read-only
	STATUS		current
	DESCRIPTION "Trial Activation Time,
			    0=Not Set or Expired
			Oid=1.3.6.1.4.1.31968.3.1.4.1.1.8
			"
	::= { unitStatusItems 8 }

mgmtPortStatus OBJECT-TYPE
	SYNTAX		INTEGER {
		unconnected(0),
		connectedNoDhcpIp(1),
		connected10Mb(2),
		connected100Mb(3),
		connected1Gb(4)
	}
	MAX-ACCESS	read-only
	STATUS		current
	DESCRIPTION "Mgmt Port Status, where:
			    0) 'UNCONNECTED'
			    1) 'CONNECTED, NO DHCP IP'
			    2) 'Connected, 10 Mb'
			    3) 'Connected, 100 Mb'
			    4) 'Connected, 1 Gb'
			Oid=1.3.6.1.4.1.31968.3.1.4.1.1.9
			"
	::= { unitStatusItems 9 }

mgmtMacAddress OBJECT-TYPE
	SYNTAX		PhysAddress
	MAX-ACCESS	read-only
	STATUS		current
	DESCRIPTION "MAC Address
			Oid=1.3.6.1.4.1.31968.3.1.4.1.1.10
			"
	::= { unitStatusItems 10 }

refStatus OBJECT-TYPE
	SYNTAX		INTEGER {
		internalOk(0),
		lockedOk(1),
		unlockedFallback(2),
		unlockedBadInput(3),
		ocxoWarming(4)
	}
	MAX-ACCESS	read-only
	STATUS		current
	DESCRIPTION "Reference Status, where:
			    0) 'Internal, Ok'
			    1) 'Locked, Ok'
			    2) 'UNLOCKED, FALLBACK'
			    3) 'UNLOCKED, BAD INPUT'
			    4) 'OCXO Warming...'
			Oid=1.3.6.1.4.1.31968.3.1.4.1.1.11
			"
	::= { unitStatusItems 11 }

monOutVoltage OBJECT-TYPE
	SYNTAX		Unsigned32
	UNITS		"0.01 V"
	MAX-ACCESS	read-only
	STATUS		current
	DESCRIPTION "Output Voltage
			Oid=1.3.6.1.4.1.31968.3.1.4.1.1.15
			"
	::= { unitStatusItems 15 }

monInVoltage OBJECT-TYPE
	SYNTAX		Unsigned32
	UNITS		"0.1 V"
	MAX-ACCESS	read-only
	STATUS		current
	DESCRIPTION "Input Voltage
			Oid=1.3.6.1.4.1.31968.3.1.4.1.1.16
			"
	::= { unitStatusItems 16 }

dataPortStatus OBJECT-TYPE
	SYNTAX		INTEGER {
		unconnected(0),
		connected10Mb(1),
		connected100Mb(2),
		connected1Gb(3)
	}
	MAX-ACCESS	read-only
	STATUS		current
	DESCRIPTION "Data Port Status, where:
			    0) 'UNCONNECTED'
			    1) 'Connected, 10 Mb'
			    2) 'Connected, 100 Mb'
			    3) 'Connected, 1 Gb'
			Oid=1.3.6.1.4.1.31968.3.1.4.1.1.18
			"
	::= { unitStatusItems 18 }

cpuTemp OBJECT-TYPE
	SYNTAX		Integer32
	UNITS		"0.1 Degree C"
	MAX-ACCESS	read-only
	STATUS		current
	DESCRIPTION "CPU Temperature
			Oid=1.3.6.1.4.1.31968.3.1.4.1.1.20
			"
	::= { unitStatusItems 20 }

txTemp OBJECT-TYPE
	SYNTAX		Integer32
	UNITS		"0.1 Degree C"
	MAX-ACCESS	read-only
	STATUS		current
	DESCRIPTION "Tx RF Temperature
			Oid=1.3.6.1.4.1.31968.3.1.4.1.1.35
			"
	::= { unitStatusItems 35 }

fpga1Temp OBJECT-TYPE
	SYNTAX		Integer32
	UNITS		"0.1 Degree C"
	MAX-ACCESS	read-only
	STATUS		current
	DESCRIPTION "Tx FPGA 1 Temperature
			Oid=1.3.6.1.4.1.31968.3.1.4.1.1.44
			"
	::= { unitStatusItems 44 }

rxTemp OBJECT-TYPE
	SYNTAX		Integer32
	UNITS		"0.1 Degree C"
	MAX-ACCESS	read-only
	STATUS		current
	DESCRIPTION "Rx RF Temperature
			Oid=1.3.6.1.4.1.31968.3.1.4.1.1.49
			"
	::= { unitStatusItems 49 }

fpga2Temp OBJECT-TYPE
	SYNTAX		Integer32
	UNITS		"0.1 Degree C"
	MAX-ACCESS	read-only
	STATUS		current
	DESCRIPTION "Rx FPGA 2 Temperature
			Oid=1.3.6.1.4.1.31968.3.1.4.1.1.58
			"
	::= { unitStatusItems 58 }

fpga3Temp OBJECT-TYPE
	SYNTAX		Integer32
	UNITS		"0.1 Degree C"
	MAX-ACCESS	read-only
	STATUS		current
	DESCRIPTION "Rx FEC FPGA 3 Temperature
			Oid=1.3.6.1.4.1.31968.3.1.4.1.1.68
			"
	::= { unitStatusItems 68 }

unitCalStatus OBJECT-TYPE
	SYNTAX		DisplayString
	MAX-ACCESS	read-only
	STATUS		current
	DESCRIPTION "Cal Task Status
			Oid=1.3.6.1.4.1.31968.3.1.4.1.1.72
			"
	::= { unitStatusItems 72 }

unitRefCal OBJECT-TYPE
	SYNTAX		DisplayString
	MAX-ACCESS	read-only
	STATUS		current
	DESCRIPTION "Reference Cal Status
			Oid=1.3.6.1.4.1.31968.3.1.4.1.1.73
			"
	::= { unitStatusItems 73 }

overTempShutdowns OBJECT-TYPE
	SYNTAX		Unsigned32
	UNITS		"1"
	MAX-ACCESS	read-only
	STATUS		current
	DESCRIPTION "Over Temp Shutdowns
			Oid=1.3.6.1.4.1.31968.3.1.4.1.1.74
			"
	::= { unitStatusItems 74 }

tleDatabase OBJECT-TYPE
	SYNTAX		DisplayString
	MAX-ACCESS	read-only
	STATUS		current
	DESCRIPTION "TLE Database File
			Oid=1.3.6.1.4.1.31968.3.1.4.1.1.75
			"
	::= { unitStatusItems 75 }

satName OBJECT-TYPE
	SYNTAX		DisplayString
	MAX-ACCESS	read-only
	STATUS		current
	DESCRIPTION "Name
			Oid=1.3.6.1.4.1.31968.3.1.4.1.1.76
			"
	::= { unitStatusItems 76 }

satCatalog OBJECT-TYPE
	SYNTAX		Unsigned32
	UNITS		"1"
	MAX-ACCESS	read-only
	STATUS		current
	DESCRIPTION "Catalog Number
			Oid=1.3.6.1.4.1.31968.3.1.4.1.1.77
			"
	::= { unitStatusItems 77 }

satClassification OBJECT-TYPE
	SYNTAX		DisplayString
	MAX-ACCESS	read-only
	STATUS		current
	DESCRIPTION "Classification
			Oid=1.3.6.1.4.1.31968.3.1.4.1.1.78
			"
	::= { unitStatusItems 78 }

satLaunchYear OBJECT-TYPE
	SYNTAX		Unsigned32
	UNITS		"1"
	MAX-ACCESS	read-only
	STATUS		current
	DESCRIPTION "Launch Year
			Oid=1.3.6.1.4.1.31968.3.1.4.1.1.79
			"
	::= { unitStatusItems 79 }

satLaunchNumber OBJECT-TYPE
	SYNTAX		Unsigned32
	UNITS		"1"
	MAX-ACCESS	read-only
	STATUS		current
	DESCRIPTION "Launch Number of the Year
			Oid=1.3.6.1.4.1.31968.3.1.4.1.1.80
			"
	::= { unitStatusItems 80 }

satLaunchPiece OBJECT-TYPE
	SYNTAX		DisplayString
	MAX-ACCESS	read-only
	STATUS		current
	DESCRIPTION "Piece Of The Launch
			Oid=1.3.6.1.4.1.31968.3.1.4.1.1.81
			"
	::= { unitStatusItems 81 }

satEphemeris OBJECT-TYPE
	SYNTAX		DisplayString
	MAX-ACCESS	read-only
	STATUS		current
	DESCRIPTION "Ephemeris Type
			Oid=1.3.6.1.4.1.31968.3.1.4.1.1.82
			"
	::= { unitStatusItems 82 }

satEpochYear OBJECT-TYPE
	SYNTAX		Unsigned32
	UNITS		"1"
	MAX-ACCESS	read-only
	STATUS		current
	DESCRIPTION "Epoch Year
			Oid=1.3.6.1.4.1.31968.3.1.4.1.1.83
			"
	::= { unitStatusItems 83 }

satEpochDay OBJECT-TYPE
	SYNTAX		DisplayString(SIZE(1..14))
	MAX-ACCESS	read-only
	STATUS		current
	DESCRIPTION "Epoch Day,
			    Text Number, Decimal Floating Point
			Oid=1.3.6.1.4.1.31968.3.1.4.1.1.84
			"
	::= { unitStatusItems 84 }

satRevolution OBJECT-TYPE
	SYNTAX		Unsigned32
	UNITS		"1"
	MAX-ACCESS	read-only
	STATUS		current
	DESCRIPTION "Revolution Number At Epoch
			Oid=1.3.6.1.4.1.31968.3.1.4.1.1.85
			"
	::= { unitStatusItems 85 }

tleSetNumber OBJECT-TYPE
	SYNTAX		Unsigned32
	UNITS		"1"
	MAX-ACCESS	read-only
	STATUS		current
	DESCRIPTION "TLE Set Number
			Oid=1.3.6.1.4.1.31968.3.1.4.1.1.86
			"
	::= { unitStatusItems 86 }

satMeanMotion OBJECT-TYPE
	SYNTAX		DisplayString(SIZE(1..14))
	MAX-ACCESS	read-only
	STATUS		current
	DESCRIPTION "Mean Motion,
			    Text Number, Decimal Floating Point
			Oid=1.3.6.1.4.1.31968.3.1.4.1.1.87
			"
	::= { unitStatusItems 87 }

satFirstMotion OBJECT-TYPE
	SYNTAX		DisplayString(SIZE(1..14))
	MAX-ACCESS	read-only
	STATUS		current
	DESCRIPTION "1st Derivative Motion,
			    Text Number, Decimal Floating Point
			Oid=1.3.6.1.4.1.31968.3.1.4.1.1.88
			"
	::= { unitStatusItems 88 }

satSecondMotion OBJECT-TYPE
	SYNTAX		DisplayString(SIZE(1..14))
	MAX-ACCESS	read-only
	STATUS		current
	DESCRIPTION "2nd Derivative Motion,
			    Text Number, Decimal Floating Point
			Oid=1.3.6.1.4.1.31968.3.1.4.1.1.89
			"
	::= { unitStatusItems 89 }

satDrag OBJECT-TYPE
	SYNTAX		DisplayString(SIZE(1..14))
	MAX-ACCESS	read-only
	STATUS		current
	DESCRIPTION "B* Drag Term,
			    Text Number, Decimal Floating Point
			Oid=1.3.6.1.4.1.31968.3.1.4.1.1.90
			"
	::= { unitStatusItems 90 }

satInclination OBJECT-TYPE
	SYNTAX		DisplayString(SIZE(1..10))
	UNITS		"Degree"
	MAX-ACCESS	read-only
	STATUS		current
	DESCRIPTION "Inclination,
			    Text Number, Decimal Floating Point
			Oid=1.3.6.1.4.1.31968.3.1.4.1.1.91
			"
	::= { unitStatusItems 91 }

satAscension OBJECT-TYPE
	SYNTAX		DisplayString(SIZE(1..10))
	UNITS		"Degree"
	MAX-ACCESS	read-only
	STATUS		current
	DESCRIPTION "Right Ascension,
			    Text Number, Decimal Floating Point
			Oid=1.3.6.1.4.1.31968.3.1.4.1.1.92
			"
	::= { unitStatusItems 92 }

satEccentricity OBJECT-TYPE
	SYNTAX		DisplayString(SIZE(1..13))
	MAX-ACCESS	read-only
	STATUS		current
	DESCRIPTION "Eccentricity,
			    Text Number, Decimal Floating Point
			Oid=1.3.6.1.4.1.31968.3.1.4.1.1.93
			"
	::= { unitStatusItems 93 }

satPerigee OBJECT-TYPE
	SYNTAX		DisplayString(SIZE(1..10))
	UNITS		"Degree"
	MAX-ACCESS	read-only
	STATUS		current
	DESCRIPTION "Argument Of Perigee,
			    Text Number, Decimal Floating Point
			Oid=1.3.6.1.4.1.31968.3.1.4.1.1.94
			"
	::= { unitStatusItems 94 }

satAnomaly OBJECT-TYPE
	SYNTAX		DisplayString(SIZE(1..10))
	UNITS		"Degree"
	MAX-ACCESS	read-only
	STATUS		current
	DESCRIPTION "Mean Anomaly,
			    Text Number, Decimal Floating Point
			Oid=1.3.6.1.4.1.31968.3.1.4.1.1.95
			"
	::= { unitStatusItems 95 }

snmpInformTotalRetryTime OBJECT-TYPE
	SYNTAX		Unsigned32
	UNITS		"0.1 s"
	MAX-ACCESS	read-only
	STATUS		current
	DESCRIPTION "Inform Total Retry Time
			Oid=1.3.6.1.4.1.31968.3.1.4.1.1.96
			"
	::= { unitStatusItems 96 }

batteryVoltage OBJECT-TYPE
	SYNTAX		Unsigned32
	UNITS		"0.001 V"
	MAX-ACCESS	read-only
	STATUS		current
	DESCRIPTION "Battery Voltage
			Oid=1.3.6.1.4.1.31968.3.1.4.1.1.97
			"
	::= { unitStatusItems 97 }

fipsStatus OBJECT-TYPE
	SYNTAX		INTEGER {
		off(0),
		selfTestPassedDataEncrypted(1),
		selfTestPassedDataNotEncrypted(2),
		softwareSelfTestFailedAlarm(3),
		hardwareSelfTestFailedAlarm(4)
	}
	MAX-ACCESS	read-only
	STATUS		current
	DESCRIPTION "FIPS Status, where:
			    0) 'Off'
			    1) 'Self Test Passed, Data Encrypted'
			    2) 'Self Test Passed, DATA NOT ENCRYPTED'
			    3) 'SOFTWARE SELF TEST FAILED ALARM'
			    4) 'HARDWARE SELF TEST FAILED ALARM'
			Oid=1.3.6.1.4.1.31968.3.1.4.1.1.102
			"
	::= { unitStatusItems 102 }

snmpAlert1InformStatus OBJECT-TYPE
	SYNTAX		INTEGER {
		receivedOk(0),
		noResponse(1),
		discoveryInProcess(2),
		discoveryOk(3),
		discoveryFailed(4),
		notAvailable(5)
	}
	MAX-ACCESS	read-only
	STATUS		current
	DESCRIPTION "Alert 1 Inform Status, where:
			    0) 'Received OK'
			    1) 'No Response'
			    2) 'Discovery In Process'
			    3) 'Discovery OK'
			    4) 'Discovery Failed'
			    5) 'Not Available'
			Oid=1.3.6.1.4.1.31968.3.1.4.1.1.103
			"
	::= { unitStatusItems 103 }

snmpAlert2InformStatus OBJECT-TYPE
	SYNTAX		INTEGER {
		receivedOk(0),
		noResponse(1),
		discoveryInProcess(2),
		discoveryOk(3),
		discoveryFailed(4),
		notAvailable(5)
	}
	MAX-ACCESS	read-only
	STATUS		current
	DESCRIPTION "Alert 2 Inform Status, where:
			    0) 'Received OK'
			    1) 'No Response'
			    2) 'Discovery In Process'
			    3) 'Discovery OK'
			    4) 'Discovery Failed'
			    5) 'Not Available'
			Oid=1.3.6.1.4.1.31968.3.1.4.1.1.104
			"
	::= { unitStatusItems 104 }

snmpAlert3InformStatus OBJECT-TYPE
	SYNTAX		INTEGER {
		receivedOk(0),
		noResponse(1),
		discoveryInProcess(2),
		discoveryOk(3),
		discoveryFailed(4),
		notAvailable(5)
	}
	MAX-ACCESS	read-only
	STATUS		current
	DESCRIPTION "Alert 3 Inform Status, where:
			    0) 'Received OK'
			    1) 'No Response'
			    2) 'Discovery In Process'
			    3) 'Discovery OK'
			    4) 'Discovery Failed'
			    5) 'Not Available'
			Oid=1.3.6.1.4.1.31968.3.1.4.1.1.105
			"
	::= { unitStatusItems 105 }

snmpAlert4InformStatus OBJECT-TYPE
	SYNTAX		INTEGER {
		receivedOk(0),
		noResponse(1),
		discoveryInProcess(2),
		discoveryOk(3),
		discoveryFailed(4),
		notAvailable(5)
	}
	MAX-ACCESS	read-only
	STATUS		current
	DESCRIPTION "Alert 4 Inform Status, where:
			    0) 'Received OK'
			    1) 'No Response'
			    2) 'Discovery In Process'
			    3) 'Discovery OK'
			    4) 'Discovery Failed'
			    5) 'Not Available'
			Oid=1.3.6.1.4.1.31968.3.1.4.1.1.106
			"
	::= { unitStatusItems 106 }

snmpAuthEngineId OBJECT-TYPE
	SYNTAX		DisplayString
	MAX-ACCESS	read-only
	STATUS		current
	DESCRIPTION "Authoritative Engine ID
			Oid=1.3.6.1.4.1.31968.3.1.4.1.1.107
			"
	::= { unitStatusItems 107 }

snmpAuthEngineBoots OBJECT-TYPE
	SYNTAX		Unsigned32
	UNITS		"1"
	MAX-ACCESS	read-only
	STATUS		current
	DESCRIPTION "Authoritative Engine Boots
			Oid=1.3.6.1.4.1.31968.3.1.4.1.1.108
			"
	::= { unitStatusItems 108 }

unitBoots OBJECT-TYPE
	SYNTAX		Unsigned32
	UNITS		"1"
	MAX-ACCESS	read-only
	STATUS		current
	DESCRIPTION "Unit Boots
			Oid=1.3.6.1.4.1.31968.3.1.4.1.1.109
			"
	::= { unitStatusItems 109 }

acuStatus OBJECT-TYPE
	SYNTAX		INTEGER {
		modemMayTransmit(0),
		cableUnwrap(1),
		blockageZone(2),
		rfHazardZone(3),
		sidelobeCheck(4),
		elevationLimit(5),
		azSkewLimit(6),
		gyroCap(7),
		acuSearchState(8),
		rssiBelowThreshold(9),
		initializing(10),
		lnbVoltageError(11),
		bucVoltageError(12),
		rfConfigurationError(13),
		rfCommunicationError(14),
		onGround(15),
		geographicRestriction(16),
		hardwareMuteSwitch(17),
		blockageWarning(18),
		rfAcuResourcesBusy(19),
		acuMutedByModem(20),
		peaking(21),
		pendingOperatorAuthorization(22),
		solarOutage(23),
		stabilisationError(24),
		motorErrorFailure(25),
		encoderErrorFailure(26),
		sensorErrorFailure(27),
		acuCommunicationErrorFailure(28),
		powerError(29),
		acuOutOfCalibration(30),
		off(100),
		txMutedWaitingForAcuResponse(101),
		keepAliveAlarmReport(102),
		txMutedKeepAliveAlarmReport(103),
		ipConnectionAlarmReport(104),
		txMutedIpConnectionAlarmReport(105),
		keepAliveAlarm(120),
		txMutedKeepAliveAlarm(121),
		ipConnectionAlarm(122),
		txMutedIpConnectionAlarm(123),
		error(200)
	}
	MAX-ACCESS	read-only
	STATUS		current
	DESCRIPTION "Status, where:
			    0) 'Modem May Transmit'
			    1) 'Cable Unwrap'
			    2) 'Blockage Zone'
			    3) 'RF Hazard Zone'
			    4) 'Sidelobe Check'
			    5) 'Elevation Limit'
			    6) 'AZ/SKEW Limit'
			    7) 'Gyro Cap'
			    8) 'ACU Search State'
			    9) 'RSSI Below Threshold'
			    10) 'Initializing'
			    11) 'LNB Voltage Error'
			    12) 'BUC Voltage Error'
			    13) 'RF Configuration Error'
			    14) 'RF Communication Error'
			    15) 'On Ground'
			    16) 'Geographic Restriction'
			    17) 'Hardware Mute Switch'
			    18) 'Blockage Warning'
			    19) 'RF ACU Resources Busy'
			    20) 'ACU Muted by Modem'
			    21) 'Peaking'
			    22) 'Pending Operator Authorization'
			    23) 'Solar Outage'
			    24) 'Stabilisation Error'
			    25) 'Motor Error/Failure'
			    26) 'Encoder Error/Failure'
			    27) 'Sensor Error/Failure'
			    28) 'ACU Communication Error/Failure'
			    29) 'Power Error'
			    30) 'ACU Out of Calibration'
			    100) 'Off'
			    101) 'Tx Muted, Waiting For ACU Response...'
			    102) 'Keep Alive Alarm Report'
			    103) 'Tx Muted, Keep Alive Alarm Report'
			    104) 'IP Connection Alarm Report'
			    105) 'Tx Muted, IP Connection Alarm Report'
			    120) 'KEEP ALIVE ALARM'
			    121) 'Tx MUTED, KEEP ALIVE ALARM'
			    122) 'IP CONNECTION ALARM'
			    123) 'Tx MUTED, IP CONNECTION ALARM'
			    200) 'ERROR'
			Oid=1.3.6.1.4.1.31968.3.1.4.1.1.119
			"
	::= { unitStatusItems 119 }

acuFunctional OBJECT-TYPE
	SYNTAX		INTEGER {
		no(0),
		yes(1)
	}
	MAX-ACCESS	read-only
	STATUS		current
	DESCRIPTION "Functional, where:
			    0) 'NO'
			    1) 'Yes'
			Oid=1.3.6.1.4.1.31968.3.1.4.1.1.120
			"
	::= { unitStatusItems 120 }

acuTxAllowed OBJECT-TYPE
	SYNTAX		INTEGER {
		no(0),
		yes(1)
	}
	MAX-ACCESS	read-only
	STATUS		current
	DESCRIPTION "Tx Allowed, where:
			    0) 'NO'
			    1) 'Yes'
			Oid=1.3.6.1.4.1.31968.3.1.4.1.1.121
			"
	::= { unitStatusItems 121 }

acuTxDisabled OBJECT-TYPE
	SYNTAX		INTEGER {
		no(0),
		yes(1)
	}
	MAX-ACCESS	read-only
	STATUS		current
	DESCRIPTION "Tx Disabled, where:
			    0) 'No'
			    1) 'YES'
			Oid=1.3.6.1.4.1.31968.3.1.4.1.1.122
			"
	::= { unitStatusItems 122 }

acuId OBJECT-TYPE
	SYNTAX		DisplayString
	MAX-ACCESS	read-only
	STATUS		current
	DESCRIPTION "ID
			Oid=1.3.6.1.4.1.31968.3.1.4.1.1.123
			"
	::= { unitStatusItems 123 }

acuGpsLocation OBJECT-TYPE
	SYNTAX		INTEGER {
		notValid(0),
		valid(1)
	}
	MAX-ACCESS	read-only
	STATUS		current
	DESCRIPTION "GPS Location, where:
			    0) 'Not Valid'
			    1) 'Valid'
			Oid=1.3.6.1.4.1.31968.3.1.4.1.1.124
			"
	::= { unitStatusItems 124 }

acuGpsTime OBJECT-TYPE
	SYNTAX		DisplayString(SIZE(1..24))
	UNITS		"0.001 s"
	MAX-ACCESS	read-only
	STATUS		current
	DESCRIPTION "GPS Time,
			    Text Number, Decimal
			Oid=1.3.6.1.4.1.31968.3.1.4.1.1.125
			"
	::= { unitStatusItems 125 }

acuGpsLatitude OBJECT-TYPE
	SYNTAX		Integer32
	MAX-ACCESS	read-only
	STATUS		current
	DESCRIPTION "GPS Latitude
			Oid=1.3.6.1.4.1.31968.3.1.4.1.1.126
			"
	::= { unitStatusItems 126 }

acuGpsLongitude OBJECT-TYPE
	SYNTAX		Integer32
	MAX-ACCESS	read-only
	STATUS		current
	DESCRIPTION "GPS Longitude
			Oid=1.3.6.1.4.1.31968.3.1.4.1.1.127
			"
	::= { unitStatusItems 127 }

acuGpsAltitude OBJECT-TYPE
	SYNTAX		Integer32
	MAX-ACCESS	read-only
	STATUS		current
	DESCRIPTION "GPS Altitude
			Oid=1.3.6.1.4.1.31968.3.1.4.1.1.128
			"
	::= { unitStatusItems 128 }

acuGpsHeading OBJECT-TYPE
	SYNTAX		Unsigned32
	MAX-ACCESS	read-only
	STATUS		current
	DESCRIPTION "GPS Heading
			Oid=1.3.6.1.4.1.31968.3.1.4.1.1.129
			"
	::= { unitStatusItems 129 }

acuGpsSpeed OBJECT-TYPE
	SYNTAX		Integer32
	MAX-ACCESS	read-only
	STATUS		current
	DESCRIPTION "GPS Speed
			Oid=1.3.6.1.4.1.31968.3.1.4.1.1.130
			"
	::= { unitStatusItems 130 }

acuGpsPitch OBJECT-TYPE
	SYNTAX		Unsigned32
	MAX-ACCESS	read-only
	STATUS		current
	DESCRIPTION "GPS Pitch
			Oid=1.3.6.1.4.1.31968.3.1.4.1.1.131
			"
	::= { unitStatusItems 131 }

acuGpsRoll OBJECT-TYPE
	SYNTAX		Unsigned32
	MAX-ACCESS	read-only
	STATUS		current
	DESCRIPTION "GPS Roll
			Oid=1.3.6.1.4.1.31968.3.1.4.1.1.132
			"
	::= { unitStatusItems 132 }

acuGpsYaw OBJECT-TYPE
	SYNTAX		Unsigned32
	MAX-ACCESS	read-only
	STATUS		current
	DESCRIPTION "GPS Yaw
			Oid=1.3.6.1.4.1.31968.3.1.4.1.1.133
			"
	::= { unitStatusItems 133 }

acuGpsSkew OBJECT-TYPE
	SYNTAX		Unsigned32
	MAX-ACCESS	read-only
	STATUS		current
	DESCRIPTION "GPS Skew
			Oid=1.3.6.1.4.1.31968.3.1.4.1.1.134
			"
	::= { unitStatusItems 134 }

acuSearchCount OBJECT-TYPE
	SYNTAX		Unsigned32
	UNITS		"1"
	MAX-ACCESS	read-only
	STATUS		current
	DESCRIPTION "Find Satellite Search Count
			Oid=1.3.6.1.4.1.31968.3.1.4.1.1.135
			"
	::= { unitStatusItems 135 }

acuLockStatInterval OBJECT-TYPE
	SYNTAX		Integer32
	UNITS		"s"
	MAX-ACCESS	read-only
	STATUS		current
	DESCRIPTION "Lock Status Interval
			Oid=1.3.6.1.4.1.31968.3.1.4.1.1.136
			"
	::= { unitStatusItems 136 }

acuConRate OBJECT-TYPE
	SYNTAX		Integer32
	UNITS		"1 Hz"
	MAX-ACCESS	read-only
	STATUS		current
	DESCRIPTION "Conical Reporting Rate,
			    0=Off
			Oid=1.3.6.1.4.1.31968.3.1.4.1.1.137
			"
	::= { unitStatusItems 137 }

acuAzPos OBJECT-TYPE
	SYNTAX		Integer32
	MAX-ACCESS	read-only
	STATUS		current
	DESCRIPTION "+AZ
			Oid=1.3.6.1.4.1.31968.3.1.4.1.1.138
			"
	::= { unitStatusItems 138 }

acuAzNeg OBJECT-TYPE
	SYNTAX		Integer32
	MAX-ACCESS	read-only
	STATUS		current
	DESCRIPTION "-AZ
			Oid=1.3.6.1.4.1.31968.3.1.4.1.1.139
			"
	::= { unitStatusItems 139 }

acuElPos OBJECT-TYPE
	SYNTAX		Integer32
	MAX-ACCESS	read-only
	STATUS		current
	DESCRIPTION "+EL
			Oid=1.3.6.1.4.1.31968.3.1.4.1.1.140
			"
	::= { unitStatusItems 140 }

acuElNeg OBJECT-TYPE
	SYNTAX		Integer32
	MAX-ACCESS	read-only
	STATUS		current
	DESCRIPTION "-EL
			Oid=1.3.6.1.4.1.31968.3.1.4.1.1.141
			"
	::= { unitStatusItems 141 }

redunStatus OBJECT-TYPE
	SYNTAX		INTEGER {
		standAlone(0),
		ready1For1Online(1),
		ready1For1Offline(2),
		primaryPartnerPrimary(3),
		backupPartnerBackup(4),
		onlinePartnerAlarm(5),
		alarmPartnerOnline(6),
		alarmPartnerAlarm(7),
		configClash(8),
		hwClash(9),
		commsLost(10),
		failOverOffline(11),
		onlinePartnerOffline(12)
	}
	MAX-ACCESS	read-only
	STATUS		current
	DESCRIPTION "Redundancy Status, where:
			    0) 'Stand Alone'
			    1) 'Ready, 1 for 1, ONLINE'
			    2) 'Ready, 1 for 1, OFFLINE'
			    3) 'PRIMARY, Partner PRIMARY'
			    4) 'BACKUP, Partner BACKUP'
			    5) 'ONLINE, Partner ALARM'
			    6) 'ALARM, Partner ONLINE'
			    7) 'ALARM, Partner ALARM'
			    8) 'CONFIG Clash'
			    9) 'HW Clash'
			    10) 'Comms Lost'
			    11) 'Fail Over, OFFLINE'
			    12) 'ONLINE, Partner OFFLINE'
			Oid=1.3.6.1.4.1.31968.3.1.4.1.1.142
			"
	::= { unitStatusItems 142 }

fipsAssembly OBJECT-TYPE
	SYNTAX		DisplayString
	MAX-ACCESS	read-only
	STATUS		current
	DESCRIPTION "FIPS Assembly
			Oid=1.3.6.1.4.1.31968.3.1.4.1.1.143
			"
	::= { unitStatusItems 143 }

fipsFpgaId OBJECT-TYPE
	SYNTAX		DisplayString
	MAX-ACCESS	read-only
	STATUS		current
	DESCRIPTION "FIPS FPGA ID
			Oid=1.3.6.1.4.1.31968.3.1.4.1.1.144
			"
	::= { unitStatusItems 144 }

fipsFpgaBuild OBJECT-TYPE
	SYNTAX		DisplayString
	MAX-ACCESS	read-only
	STATUS		current
	DESCRIPTION "FIPS FPGA Build
			Oid=1.3.6.1.4.1.31968.3.1.4.1.1.145
			"
	::= { unitStatusItems 145 }

fipsSn OBJECT-TYPE
	SYNTAX		DisplayString(SIZE(1..24))
	UNITS		"1"
	MAX-ACCESS	read-only
	STATUS		current
	DESCRIPTION "FIPS SN,
			    Text Number, Decimal
			Oid=1.3.6.1.4.1.31968.3.1.4.1.1.146
			"
	::= { unitStatusItems 146 }

fipsSelfTests OBJECT-TYPE
	SYNTAX		Unsigned32
	UNITS		"1"
	MAX-ACCESS	read-only
	STATUS		current
	DESCRIPTION "FIPS Self Tests
			Oid=1.3.6.1.4.1.31968.3.1.4.1.1.147
			"
	::= { unitStatusItems 147 }

fipsTemp OBJECT-TYPE
	SYNTAX		Integer32
	UNITS		"0.1 Degree C"
	MAX-ACCESS	read-only
	STATUS		current
	DESCRIPTION "FIPS FPGA Temperature
			Oid=1.3.6.1.4.1.31968.3.1.4.1.1.151
			"
	::= { unitStatusItems 151 }

fipsLastLog OBJECT-TYPE
	SYNTAX		INTEGER {
		empty(0),
		n33vAlarm(1),
		n25vAlarm(2),
		n18vAlarm(3),
		n10vAlarm(4),
		temperatureAlarm(5),
		decryptorSelfTestFault(10),
		encryptorSelfTestFault(11),
		decryptorCompareFault(12),
		encryptorCompareFault(13),
		trnSelfTestFault(14),
		sha3256SelfTestFault(15),
		roundKeySelfTestFault(16),
		kmacSelfTestFault(17)
	}
	MAX-ACCESS	read-only
	STATUS		current
	DESCRIPTION "FIPS Last Hardware Alarm/Fault Log, where:
			    0) 'Empty'
			    1) '3.3V ALARM'
			    2) '2.5V ALARM'
			    3) '1.8V ALARM'
			    4) '1.0V ALARM'
			    5) 'TEMPERATURE ALARM'
			    10) 'DECRYPTOR SELF TEST FAULT'
			    11) 'ENCRYPTOR SELF TEST FAULT'
			    12) 'DECRYPTOR COMPARE FAULT'
			    13) 'ENCRYPTOR COMPARE FAULT'
			    14) 'TRN SELF TEST FAULT'
			    15) 'SHA3-256 SELF TEST FAULT'
			    16) 'Round-Key SELF TEST FAULT'
			    17) 'KMAC SELF TEST FAULT'
			Oid=1.3.6.1.4.1.31968.3.1.4.1.1.160
			"
	::= { unitStatusItems 160 }

ntpServerStatus OBJECT-TYPE
	SYNTAX		INTEGER {
		notSynchronized(0),
		synchronized(1)
	}
	MAX-ACCESS	read-only
	STATUS		current
	DESCRIPTION "NTP Server Status, where:
			    0) 'NOT SYNCHRONIZED'
			    1) 'Synchronized'
			Oid=1.3.6.1.4.1.31968.3.1.4.1.1.162
			"
	::= { unitStatusItems 162 }

stationId OBJECT-TYPE
	SYNTAX		DisplayString(SIZE(0..28))
	MAX-ACCESS	read-write
	STATUS		current
	DESCRIPTION "Station ID
			Oid=1.3.6.1.4.1.31968.3.1.4.1.2.1
			"
	::= { unitConfigItems 1 }

dateTime OBJECT-TYPE
	SYNTAX		DateAndTime
	MAX-ACCESS	read-write
	STATUS		current
	DESCRIPTION "Date Time UTC
			Oid=1.3.6.1.4.1.31968.3.1.4.1.2.2
			"
	::= { unitConfigItems 2 }

powerMin OBJECT-TYPE
	SYNTAX		Unsigned32
	UNITS		"0.1 V"
	MAX-ACCESS	read-write
	STATUS		current
	DESCRIPTION "Power Input Minimum Voltage
			Oid=1.3.6.1.4.1.31968.3.1.4.1.2.3
			"
	::= { unitConfigItems 3 }

powerAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Power Input Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.2.4
			"
	::= { unitConfigItems 4 }

trial7daysAlarm OBJECT-TYPE
	SYNTAX		INTEGER {
		off(0),
		report(1),
		alarm(3),
		alarmAndRelayOutput(5)
	}
	MAX-ACCESS	read-write
	STATUS		current
	DESCRIPTION "Trial < 7 Days Remaining Alarm, where:
			    0) 'Off'
			    1) 'Report'
			    3) 'Alarm'
			    5) 'Alarm & Relay Output'
			Oid=1.3.6.1.4.1.31968.3.1.4.1.2.5
			"
	::= { unitConfigItems 5 }

trial24hoursAlarm OBJECT-TYPE
	SYNTAX		INTEGER {
		off(0),
		report(1),
		alarm(3),
		alarmAndRelayOutput(5)
	}
	MAX-ACCESS	read-write
	STATUS		current
	DESCRIPTION "Trial < 24 Hours Remaining Alarm, where:
			    0) 'Off'
			    1) 'Report'
			    3) 'Alarm'
			    5) 'Alarm & Relay Output'
			Oid=1.3.6.1.4.1.31968.3.1.4.1.2.6
			"
	::= { unitConfigItems 6 }

unitTestAlarm OBJECT-TYPE
	SYNTAX		INTEGER {
		off(0),
		report(1),
		reportAndMuteTxOutput(2),
		alarm(3),
		alarmAndMuteTxOutput(4),
		alarmAndRelayOutput(5),
		alarmAndRelayOutputAndMuteTxOutput(6)
	}
	MAX-ACCESS	read-write
	STATUS		current
	DESCRIPTION "Test Active Alarm, where:
			    0) 'Off'
			    1) 'Report'
			    2) 'Report & Mute Tx Output'
			    3) 'Alarm'
			    4) 'Alarm & Mute Tx Output'
			    5) 'Alarm & Relay Output'
			    6) 'Alarm & Relay Output & Mute Tx Output'
			Oid=1.3.6.1.4.1.31968.3.1.4.1.2.7
			"
	::= { unitConfigItems 7 }

hardwareAlarm OBJECT-TYPE
	SYNTAX		INTEGER {
		alarm(0),
		alarmAndRelayOutput(1),
		alarmAndMuteTxOutput(2),
		alarmAndRelayOutputAndMuteTxOutput(3)
	}
	MAX-ACCESS	read-write
	STATUS		current
	DESCRIPTION "Hardware Alarm, where:
			    0) 'Alarm'
			    1) 'Alarm & Relay Output'
			    2) 'Alarm & Mute Tx Output'
			    3) 'Alarm & Relay Output & Mute Tx Output'
			Oid=1.3.6.1.4.1.31968.3.1.4.1.2.8
			"
	::= { unitConfigItems 8 }

reboot OBJECT-TYPE
	SYNTAX		INTEGER {
		normal(0),
		rebootNow(1),
		rebootAfter30Seconds(2),
		rebootAfter2Minutes(3),
		rebootAfter10Minutes(4)
	}
	MAX-ACCESS	read-write
	STATUS		current
	DESCRIPTION "Boot Control, where:
			    0) 'Normal'
			    1) 'Reboot Now'
			    2) 'Reboot After 30 Seconds'
			    3) 'Reboot After 2 Minutes'
			    4) 'Reboot After 10 Minutes'
			Oid=1.3.6.1.4.1.31968.3.1.4.1.2.9
			"
	::= { unitConfigItems 9 }

featureActivation OBJECT-TYPE
	SYNTAX		DisplayString(SIZE(29))
	MAX-ACCESS	read-write
	STATUS		current
	DESCRIPTION "Feature Activation,
			    '#####-#####-#####-#####-#####'
			Oid=1.3.6.1.4.1.31968.3.1.4.1.2.10
			"
	::= { unitConfigItems 10 }

trialActivation OBJECT-TYPE
	SYNTAX		DisplayString(SIZE(29))
	MAX-ACCESS	read-write
	STATUS		current
	DESCRIPTION "Trial Activation,
			    '#####-#####-#####-#####-#####'
			Oid=1.3.6.1.4.1.31968.3.1.4.1.2.11
			"
	::= { unitConfigItems 11 }

admin OBJECT-TYPE
	SYNTAX		INTEGER {
		normal(0),
		on(1)
	}
	MAX-ACCESS	read-write
	STATUS		current
	DESCRIPTION "Admin, where:
			    0) 'Normal'
			    1) 'On'
			Oid=1.3.6.1.4.1.31968.3.1.4.1.2.12
			"
	::= { unitConfigItems 12 }

httpServerProtocol OBJECT-TYPE
	SYNTAX		INTEGER {
		http(0),
		https(1)
	}
	MAX-ACCESS	read-write
	STATUS		current
	DESCRIPTION "Server Protocol, where:
			    0) 'HTTP'
			    1) 'HTTPS'
			Oid=1.3.6.1.4.1.31968.3.1.4.1.2.13
			"
	::= { unitConfigItems 13 }

httpReadName OBJECT-TYPE
	SYNTAX		DisplayString(SIZE(5..28))
	MAX-ACCESS	read-write
	STATUS		current
	DESCRIPTION "Read Access Name
			Oid=1.3.6.1.4.1.31968.3.1.4.1.2.14
			"
	::= { unitConfigItems 14 }

httpReadPassword OBJECT-TYPE
	SYNTAX		DisplayString(SIZE(5..28))
	MAX-ACCESS	read-write
	STATUS		current
	DESCRIPTION "Read Access Password
			Oid=1.3.6.1.4.1.31968.3.1.4.1.2.15
			"
	::= { unitConfigItems 15 }

httpFullName OBJECT-TYPE
	SYNTAX		DisplayString(SIZE(5..28))
	MAX-ACCESS	read-write
	STATUS		current
	DESCRIPTION "Full Access Name
			Oid=1.3.6.1.4.1.31968.3.1.4.1.2.16
			"
	::= { unitConfigItems 16 }

httpFullPassword OBJECT-TYPE
	SYNTAX		DisplayString(SIZE(5..28))
	MAX-ACCESS	read-write
	STATUS		current
	DESCRIPTION "Full Access Password
			Oid=1.3.6.1.4.1.31968.3.1.4.1.2.17
			"
	::= { unitConfigItems 17 }

httpActivity OBJECT-TYPE
	SYNTAX		INTEGER {
		none(0),
		flashOnline(1)
	}
	MAX-ACCESS	read-write
	STATUS		current
	DESCRIPTION "Activity, where:
			    0) 'None'
			    1) 'Flash Online'
			Oid=1.3.6.1.4.1.31968.3.1.4.1.2.18
			"
	::= { unitConfigItems 18 }

snmpAgentMode OBJECT-TYPE
	SYNTAX		INTEGER {
		off(0),
		readOnly(1),
		fullAccess(2)
	}
	MAX-ACCESS	read-write
	STATUS		current
	DESCRIPTION "Agent Mode, where:
			    0) 'Off'
			    1) 'Read Only'
			    2) 'Full Access'
			Oid=1.3.6.1.4.1.31968.3.1.4.1.2.19
			"
	::= { unitConfigItems 19 }

snmpAgentProtocol OBJECT-TYPE
	SYNTAX		INTEGER {
		v1(0),
		v2c(1),
		v3(2)
	}
	MAX-ACCESS	read-write
	STATUS		current
	DESCRIPTION "Agent Protocol, where:
			    0) 'V1'
			    1) 'V2c'
			    2) 'V3'
			Oid=1.3.6.1.4.1.31968.3.1.4.1.2.20
			"
	::= { unitConfigItems 20 }

snmpAgentPort OBJECT-TYPE
	SYNTAX		Unsigned32
	UNITS		"1"
	MAX-ACCESS	read-write
	STATUS		current
	DESCRIPTION "Agent Port Number
			Oid=1.3.6.1.4.1.31968.3.1.4.1.2.21
			"
	::= { unitConfigItems 21 }

snmpReadName OBJECT-TYPE
	SYNTAX		DisplayString(SIZE(5..28))
	MAX-ACCESS	read-write
	STATUS		current
	DESCRIPTION "Read Only Community
			Oid=1.3.6.1.4.1.31968.3.1.4.1.2.22
			"
	::= { unitConfigItems 22 }

snmpFullName OBJECT-TYPE
	SYNTAX		DisplayString(SIZE(5..28))
	MAX-ACCESS	read-write
	STATUS		current
	DESCRIPTION "Read/Write Community
			Oid=1.3.6.1.4.1.31968.3.1.4.1.2.23
			"
	::= { unitConfigItems 23 }

snmpAlert1Name OBJECT-TYPE
	SYNTAX		DisplayString(SIZE(5..28))
	MAX-ACCESS	read-write
	STATUS		current
	DESCRIPTION "Alert 1 Community
			Oid=1.3.6.1.4.1.31968.3.1.4.1.2.24
			"
	::= { unitConfigItems 24 }

snmpAlert2Name OBJECT-TYPE
	SYNTAX		DisplayString(SIZE(5..28))
	MAX-ACCESS	read-write
	STATUS		current
	DESCRIPTION "Alert 2 Community
			Oid=1.3.6.1.4.1.31968.3.1.4.1.2.25
			"
	::= { unitConfigItems 25 }

snmpAlert3Name OBJECT-TYPE
	SYNTAX		DisplayString(SIZE(5..28))
	MAX-ACCESS	read-write
	STATUS		current
	DESCRIPTION "Alert 3 Community
			Oid=1.3.6.1.4.1.31968.3.1.4.1.2.26
			"
	::= { unitConfigItems 26 }

snmpAlert4Name OBJECT-TYPE
	SYNTAX		DisplayString(SIZE(5..28))
	MAX-ACCESS	read-write
	STATUS		current
	DESCRIPTION "Alert 4 Community
			Oid=1.3.6.1.4.1.31968.3.1.4.1.2.27
			"
	::= { unitConfigItems 27 }

snmpAlert1Mode OBJECT-TYPE
	SYNTAX		INTEGER {
		off(0),
		trapNotification(1),
		inform(2)
	}
	MAX-ACCESS	read-write
	STATUS		current
	DESCRIPTION "Alert 1 Mode, where:
			    0) 'Off'
			    1) 'Trap/Notification'
			    2) 'Inform'
			Oid=1.3.6.1.4.1.31968.3.1.4.1.2.28
			"
	::= { unitConfigItems 28 }

snmpAlert2Mode OBJECT-TYPE
	SYNTAX		INTEGER {
		off(0),
		trapNotification(1),
		inform(2)
	}
	MAX-ACCESS	read-write
	STATUS		current
	DESCRIPTION "Alert 2 Mode, where:
			    0) 'Off'
			    1) 'Trap/Notification'
			    2) 'Inform'
			Oid=1.3.6.1.4.1.31968.3.1.4.1.2.29
			"
	::= { unitConfigItems 29 }

snmpAlert3Mode OBJECT-TYPE
	SYNTAX		INTEGER {
		off(0),
		trapNotification(1),
		inform(2)
	}
	MAX-ACCESS	read-write
	STATUS		current
	DESCRIPTION "Alert 3 Mode, where:
			    0) 'Off'
			    1) 'Trap/Notification'
			    2) 'Inform'
			Oid=1.3.6.1.4.1.31968.3.1.4.1.2.30
			"
	::= { unitConfigItems 30 }

snmpAlert4Mode OBJECT-TYPE
	SYNTAX		INTEGER {
		off(0),
		trapNotification(1),
		inform(2)
	}
	MAX-ACCESS	read-write
	STATUS		current
	DESCRIPTION "Alert 4 Mode, where:
			    0) 'Off'
			    1) 'Trap/Notification'
			    2) 'Inform'
			Oid=1.3.6.1.4.1.31968.3.1.4.1.2.31
			"
	::= { unitConfigItems 31 }

snmpAlert1Address OBJECT-TYPE
	SYNTAX		IpAddress
	MAX-ACCESS	read-write
	STATUS		current
	DESCRIPTION "Alert 1 Address
			Oid=1.3.6.1.4.1.31968.3.1.4.1.2.32
			"
	::= { unitConfigItems 32 }

snmpAlert2Address OBJECT-TYPE
	SYNTAX		IpAddress
	MAX-ACCESS	read-write
	STATUS		current
	DESCRIPTION "Alert 2 Address
			Oid=1.3.6.1.4.1.31968.3.1.4.1.2.33
			"
	::= { unitConfigItems 33 }

snmpAlert3Address OBJECT-TYPE
	SYNTAX		IpAddress
	MAX-ACCESS	read-write
	STATUS		current
	DESCRIPTION "Alert 3 Address
			Oid=1.3.6.1.4.1.31968.3.1.4.1.2.34
			"
	::= { unitConfigItems 34 }

snmpAlert4Address OBJECT-TYPE
	SYNTAX		IpAddress
	MAX-ACCESS	read-write
	STATUS		current
	DESCRIPTION "Alert 4 Address
			Oid=1.3.6.1.4.1.31968.3.1.4.1.2.35
			"
	::= { unitConfigItems 35 }

snmpAlert1Port OBJECT-TYPE
	SYNTAX		Unsigned32
	UNITS		"1"
	MAX-ACCESS	read-write
	STATUS		current
	DESCRIPTION "Alert 1 Port
			Oid=1.3.6.1.4.1.31968.3.1.4.1.2.36
			"
	::= { unitConfigItems 36 }

snmpAlert2Port OBJECT-TYPE
	SYNTAX		Unsigned32
	UNITS		"1"
	MAX-ACCESS	read-write
	STATUS		current
	DESCRIPTION "Alert 2 Port
			Oid=1.3.6.1.4.1.31968.3.1.4.1.2.37
			"
	::= { unitConfigItems 37 }

snmpAlert3Port OBJECT-TYPE
	SYNTAX		Unsigned32
	UNITS		"1"
	MAX-ACCESS	read-write
	STATUS		current
	DESCRIPTION "Alert 3 Port
			Oid=1.3.6.1.4.1.31968.3.1.4.1.2.38
			"
	::= { unitConfigItems 38 }

snmpAlert4Port OBJECT-TYPE
	SYNTAX		Unsigned32
	UNITS		"1"
	MAX-ACCESS	read-write
	STATUS		current
	DESCRIPTION "Alert 4 Port
			Oid=1.3.6.1.4.1.31968.3.1.4.1.2.39
			"
	::= { unitConfigItems 39 }

snmpInformRetries OBJECT-TYPE
	SYNTAX		Unsigned32
	UNITS		"1"
	MAX-ACCESS	read-write
	STATUS		current
	DESCRIPTION "Inform Retries
			Oid=1.3.6.1.4.1.31968.3.1.4.1.2.40
			"
	::= { unitConfigItems 40 }

snmpInformTimeout OBJECT-TYPE
	SYNTAX		Unsigned32
	UNITS		"0.1 s"
	MAX-ACCESS	read-write
	STATUS		current
	DESCRIPTION "Inform Timeout
			Oid=1.3.6.1.4.1.31968.3.1.4.1.2.41
			"
	::= { unitConfigItems 41 }

snmpActivity OBJECT-TYPE
	SYNTAX		INTEGER {
		none(0),
		flashOnline(1)
	}
	MAX-ACCESS	read-write
	STATUS		current
	DESCRIPTION "Activity, where:
			    0) 'None'
			    1) 'Flash Online'
			Oid=1.3.6.1.4.1.31968.3.1.4.1.2.42
			"
	::= { unitConfigItems 42 }

mgmtDhcp OBJECT-TYPE
	SYNTAX		INTEGER {
		off(0),
		on(1)
	}
	MAX-ACCESS	read-write
	STATUS		current
	DESCRIPTION "DHCP, where:
			    0) 'Off'
			    1) 'On'
			Oid=1.3.6.1.4.1.31968.3.1.4.1.2.43
			"
	::= { unitConfigItems 43 }

mgmtAddress OBJECT-TYPE
	SYNTAX		IpAddress
	MAX-ACCESS	read-write
	STATUS		current
	DESCRIPTION "Mgmt IP Address
			Oid=1.3.6.1.4.1.31968.3.1.4.1.2.44
			"
	::= { unitConfigItems 44 }

mgmtMask OBJECT-TYPE
	SYNTAX		IpAddress
	MAX-ACCESS	read-write
	STATUS		current
	DESCRIPTION "Mgmt IP Mask
			Oid=1.3.6.1.4.1.31968.3.1.4.1.2.45
			"
	::= { unitConfigItems 45 }

mgmtGateway OBJECT-TYPE
	SYNTAX		IpAddress
	MAX-ACCESS	read-write
	STATUS		current
	DESCRIPTION "Gateway,
			    0.0.0.0=Off
			Oid=1.3.6.1.4.1.31968.3.1.4.1.2.46
			"
	::= { unitConfigItems 46 }

mgmtDns1 OBJECT-TYPE
	SYNTAX		IpAddress
	MAX-ACCESS	read-write
	STATUS		current
	DESCRIPTION "DNS 1,
			    0.0.0.0=Off
			Oid=1.3.6.1.4.1.31968.3.1.4.1.2.47
			"
	::= { unitConfigItems 47 }

mgmtDns2 OBJECT-TYPE
	SYNTAX		IpAddress
	MAX-ACCESS	read-write
	STATUS		current
	DESCRIPTION "DNS 2,
			    0.0.0.0=Off
			Oid=1.3.6.1.4.1.31968.3.1.4.1.2.48
			"
	::= { unitConfigItems 48 }

mgmtUdpServerMode OBJECT-TYPE
	SYNTAX		INTEGER {
		off(0),
		readOnly(1),
		fullAccess(2)
	}
	MAX-ACCESS	read-write
	STATUS		current
	DESCRIPTION "UDP Server Mode, where:
			    0) 'Off'
			    1) 'Read Only'
			    2) 'Full Access'
			Oid=1.3.6.1.4.1.31968.3.1.4.1.2.49
			"
	::= { unitConfigItems 49 }

mgmtUdpServerPort OBJECT-TYPE
	SYNTAX		Unsigned32
	UNITS		"1"
	MAX-ACCESS	read-write
	STATUS		current
	DESCRIPTION "UDP Port Number
			Oid=1.3.6.1.4.1.31968.3.1.4.1.2.50
			"
	::= { unitConfigItems 50 }

mgmtUdpRemotePath OBJECT-TYPE
	SYNTAX		IpAddress
	MAX-ACCESS	read-write
	STATUS		current
	DESCRIPTION "UDP Remote Path,
			    0.0.0.0=Off
			Oid=1.3.6.1.4.1.31968.3.1.4.1.2.51
			"
	::= { unitConfigItems 51 }

mgmtUdpExternalUnit OBJECT-TYPE
	SYNTAX		IpAddress
	MAX-ACCESS	read-write
	STATUS		current
	DESCRIPTION "UDP External Unit,
			    0.0.0.0=Off
			Oid=1.3.6.1.4.1.31968.3.1.4.1.2.52
			"
	::= { unitConfigItems 52 }

mgmtUdpActivity OBJECT-TYPE
	SYNTAX		INTEGER {
		none(0),
		flashOnline(1)
	}
	MAX-ACCESS	read-write
	STATUS		current
	DESCRIPTION "UDP Activity, where:
			    0) 'None'
			    1) 'Flash Online'
			Oid=1.3.6.1.4.1.31968.3.1.4.1.2.53
			"
	::= { unitConfigItems 53 }

rs232Mode OBJECT-TYPE
	SYNTAX		INTEGER {
		off(0),
		readOnly(1),
		fullAccess(2)
	}
	MAX-ACCESS	read-write
	STATUS		current
	DESCRIPTION "RS-232 Mode, where:
			    0) 'Off'
			    1) 'Read Only'
			    2) 'Full Access'
			Oid=1.3.6.1.4.1.31968.3.1.4.1.2.54
			"
	::= { unitConfigItems 54 }

rs232Protocol OBJECT-TYPE
	SYNTAX		INTEGER {
		m7BinaryPacket(0),
		m7xcBinaryPacket(1)
	}
	MAX-ACCESS	read-write
	STATUS		current
	DESCRIPTION "RS-232 Protocol, where:
			    0) 'M7 Binary Packet'
			    1) 'M7XC Binary Packet'
			Oid=1.3.6.1.4.1.31968.3.1.4.1.2.55
			"
	::= { unitConfigItems 55 }

rs232Address OBJECT-TYPE
	SYNTAX		Unsigned32
	UNITS		"1"
	MAX-ACCESS	read-write
	STATUS		current
	DESCRIPTION "RS-232 Address
			Oid=1.3.6.1.4.1.31968.3.1.4.1.2.56
			"
	::= { unitConfigItems 56 }

rs232Rate OBJECT-TYPE
	SYNTAX		INTEGER {
		n300Bps(0),
		n600Bps(1),
		n1200Bps(2),
		n2400Bps(3),
		n4800Bps(4),
		n9600Bps(5),
		n19200Bps(6),
		n38400Bps(7),
		n57600Bps(8)
	}
	MAX-ACCESS	read-write
	STATUS		current
	DESCRIPTION "RS-232 Rate, where:
			    0) '300 bps'
			    1) '600 bps'
			    2) '1200 bps'
			    3) '2400 bps'
			    4) '4800 bps'
			    5) '9600 bps'
			    6) '19200 bps'
			    7) '38400 bps'
			    8) '57600 bps'
			Oid=1.3.6.1.4.1.31968.3.1.4.1.2.57
			"
	::= { unitConfigItems 57 }

rs232Format OBJECT-TYPE
	SYNTAX		INTEGER {
		n81(0),
		e81(1),
		o81(2),
		m81(3),
		s81(4)
	}
	MAX-ACCESS	read-write
	STATUS		current
	DESCRIPTION "RS-232 Format, where:
			    0) 'N,8,1'
			    1) 'E,8,1'
			    2) 'O,8,1'
			    3) 'M,8,1'
			    4) 'S,8,1'
			Oid=1.3.6.1.4.1.31968.3.1.4.1.2.58
			"
	::= { unitConfigItems 58 }

rs232Activity OBJECT-TYPE
	SYNTAX		INTEGER {
		none(0),
		flashOnline(1)
	}
	MAX-ACCESS	read-write
	STATUS		current
	DESCRIPTION "Activity, where:
			    0) 'None'
			    1) 'Flash Online'
			Oid=1.3.6.1.4.1.31968.3.1.4.1.2.59
			"
	::= { unitConfigItems 59 }

refSource OBJECT-TYPE
	SYNTAX		INTEGER {
		internalRefOutOff(0),
		internalRefOutOn(1),
		externalInput(2)
	}
	MAX-ACCESS	read-write
	STATUS		current
	DESCRIPTION "Source, where:
			    0) 'Internal, Ref Out Off'
			    1) 'Internal, Ref Out On'
			    2) 'External Input'
			Oid=1.3.6.1.4.1.31968.3.1.4.1.2.60
			"
	::= { unitConfigItems 60 }

refFrequency OBJECT-TYPE
	SYNTAX		INTEGER {
		n10Mhz(0),
		n50Mhz(1)
	}
	MAX-ACCESS	read-write
	STATUS		current
	DESCRIPTION "Frequency, where:
			    0) '10 MHz'
			    1) '50 MHz'
			Oid=1.3.6.1.4.1.31968.3.1.4.1.2.61
			"
	::= { unitConfigItems 61 }

refFineTune OBJECT-TYPE
	SYNTAX		Integer32
	UNITS		"1"
	MAX-ACCESS	read-write
	STATUS		current
	DESCRIPTION "Fine Tune
			Oid=1.3.6.1.4.1.31968.3.1.4.1.2.62
			"
	::= { unitConfigItems 62 }

eventDebounce OBJECT-TYPE
	SYNTAX		Unsigned32
	UNITS		"0.1 s"
	MAX-ACCESS	read-write
	STATUS		current
	DESCRIPTION "Debounce Time
			Oid=1.3.6.1.4.1.31968.3.1.4.1.2.63
			"
	::= { unitConfigItems 63 }

refAlarm OBJECT-TYPE
	SYNTAX		INTEGER {
		off(0),
		report(1),
		reportAndMuteTxOutput(2),
		alarm(3),
		alarmAndMuteTxOutput(4),
		alarmAndRelayOutput(5),
		alarmAndRelayOutputAndMuteTxOutput(6)
	}
	MAX-ACCESS	read-write
	STATUS		current
	DESCRIPTION "Reference Alarm, where:
			    0) 'Off'
			    1) 'Report'
			    2) 'Report & Mute Tx Output'
			    3) 'Alarm'
			    4) 'Alarm & Mute Tx Output'
			    5) 'Alarm & Relay Output'
			    6) 'Alarm & Relay Output & Mute Tx Output'
			Oid=1.3.6.1.4.1.31968.3.1.4.1.2.64
			"
	::= { unitConfigItems 64 }

refOcxoOven OBJECT-TYPE
	SYNTAX		INTEGER {
		off(0),
		report(1),
		reportAndMuteTxOutput(2),
		alarm(3),
		alarmAndMuteTxOutput(4),
		alarmAndRelayOutput(5),
		alarmAndRelayOutputAndMuteTxOutput(6)
	}
	MAX-ACCESS	read-write
	STATUS		current
	DESCRIPTION "OCXO Oven Alarm, where:
			    0) 'Off'
			    1) 'Report'
			    2) 'Report & Mute Tx Output'
			    3) 'Alarm'
			    4) 'Alarm & Mute Tx Output'
			    5) 'Alarm & Relay Output'
			    6) 'Alarm & Relay Output & Mute Tx Output'
			Oid=1.3.6.1.4.1.31968.3.1.4.1.2.65
			"
	::= { unitConfigItems 65 }

monOutMode OBJECT-TYPE
	SYNTAX		INTEGER {
		off(0),
		txLevel(1),
		txRemoteEsN0(2),
		txAcm(3),
		rx1Level(4),
		rx1EsN0(5),
		rx2Level(6),
		rx2EsN0(7),
		rx3Level(8),
		rx3EsN0(9),
		rx4Level(10),
		rx4EsN0(11),
		rx5Level(12),
		rx5EsN0(13),
		rx6Level(14),
		rx6EsN0(15),
		rx7Level(16),
		rx7EsN0(17),
		rx8Level(18),
		rx8EsN0(19),
		rx9Level(20),
		rx9EsN0(21),
		rx10Level(22),
		rx10EsN0(23),
		rx11Level(24),
		rx11EsN0(25),
		rx12Level(26),
		rx12EsN0(27),
		rx13Level(28),
		rx13EsN0(29),
		rx14Level(30),
		rx14EsN0(31),
		rx15Level(32),
		rx15EsN0(33),
		rx16Level(34),
		rx16EsN0(35)
	}
	MAX-ACCESS	read-write
	STATUS		current
	DESCRIPTION "Output Mode, where:
			    0) 'Off'
			    1) 'Tx Level'
			    2) 'Tx Remote Es/N0'
			    3) 'Tx ACM'
			    4) 'Rx 1 Level'
			    5) 'Rx 1 Es/N0'
			    6) 'Rx 2 Level'
			    7) 'Rx 2 Es/N0'
			    8) 'Rx 3 Level'
			    9) 'Rx 3 Es/N0'
			    10) 'Rx 4 Level'
			    11) 'Rx 4 Es/N0'
			    12) 'Rx 5 Level'
			    13) 'Rx 5 Es/N0'
			    14) 'Rx 6 Level'
			    15) 'Rx 6 Es/N0'
			    16) 'Rx 7 Level'
			    17) 'Rx 7 Es/N0'
			    18) 'Rx 8 Level'
			    19) 'Rx 8 Es/N0'
			    20) 'Rx 9 Level'
			    21) 'Rx 9 Es/N0'
			    22) 'Rx 10 Level'
			    23) 'Rx 10 Es/N0'
			    24) 'Rx 11 Level'
			    25) 'Rx 11 Es/N0'
			    26) 'Rx 12 Level'
			    27) 'Rx 12 Es/N0'
			    28) 'Rx 13 Level'
			    29) 'Rx 13 Es/N0'
			    30) 'Rx 14 Level'
			    31) 'Rx 14 Es/N0'
			    32) 'Rx 15 Level'
			    33) 'Rx 15 Es/N0'
			    34) 'Rx 16 Level'
			    35) 'Rx 16 Es/N0'
			Oid=1.3.6.1.4.1.31968.3.1.4.1.2.66
			"
	::= { unitConfigItems 66 }

monOutScale OBJECT-TYPE
	SYNTAX		Unsigned32
	UNITS		"0.1 V"
	MAX-ACCESS	read-write
	STATUS		current
	DESCRIPTION "Output Full Scale
			Oid=1.3.6.1.4.1.31968.3.1.4.1.2.67
			"
	::= { unitConfigItems 67 }

monOutSlope OBJECT-TYPE
	SYNTAX		INTEGER {
		positive(0),
		negative(1)
	}
	MAX-ACCESS	read-write
	STATUS		current
	DESCRIPTION "Output Slope, where:
			    0) 'Positive'
			    1) 'Negative'
			Oid=1.3.6.1.4.1.31968.3.1.4.1.2.68
			"
	::= { unitConfigItems 68 }

monAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Monitor Input Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.2.69
			"
	::= { unitConfigItems 69 }

monInThreshold OBJECT-TYPE
	SYNTAX		Unsigned32
	UNITS		"0.1 V"
	MAX-ACCESS	read-write
	STATUS		current
	DESCRIPTION "Monitor Input Threshold
			Oid=1.3.6.1.4.1.31968.3.1.4.1.2.70
			"
	::= { unitConfigItems 70 }

monInSense OBJECT-TYPE
	SYNTAX		INTEGER {
		activeLow(0),
		activeHigh(1)
	}
	MAX-ACCESS	read-write
	STATUS		current
	DESCRIPTION "Monitor Input Sense, where:
			    0) 'Active Low'
			    1) 'Active High'
			Oid=1.3.6.1.4.1.31968.3.1.4.1.2.71
			"
	::= { unitConfigItems 71 }

redundancy OBJECT-TYPE
	SYNTAX		INTEGER {
		off(0),
		report(1),
		alarm(3),
		alarmAndRelayOutput(5)
	}
	MAX-ACCESS	read-write
	STATUS		current
	DESCRIPTION "Alarm, where:
			    0) 'Off'
			    1) 'Report'
			    3) 'Alarm'
			    5) 'Alarm & Relay Output'
			Oid=1.3.6.1.4.1.31968.3.1.4.1.2.72
			"
	::= { unitConfigItems 72 }

eventPendingAlarm OBJECT-TYPE
	SYNTAX		INTEGER {
		off(0),
		report(1),
		alarm(3),
		alarmAndRelayOutput(5)
	}
	MAX-ACCESS	read-write
	STATUS		current
	DESCRIPTION "Event Pending Alarm, where:
			    0) 'Off'
			    1) 'Report'
			    3) 'Alarm'
			    5) 'Alarm & Relay Output'
			Oid=1.3.6.1.4.1.31968.3.1.4.1.2.73
			"
	::= { unitConfigItems 73 }

mgmtLinkAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Mgmt Port Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.2.74
			"
	::= { unitConfigItems 74 }

dataLinkAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Data Port Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.2.75
			"
	::= { unitConfigItems 75 }

eventDisplay OBJECT-TYPE
	SYNTAX		INTEGER {
		last20EventsAutoUpdate(0),
		last50EventsAutoUpdate(1),
		allEventsManualUpdate(2)
	}
	MAX-ACCESS	read-write
	STATUS		current
	DESCRIPTION "Displayed Events, where:
			    0) 'Last 20 Events, Auto Update'
			    1) 'Last 50 Events, Auto Update'
			    2) 'All Events, Manual Update'
			Oid=1.3.6.1.4.1.31968.3.1.4.1.2.76
			"
	::= { unitConfigItems 76 }

eventFilter OBJECT-TYPE
	SYNTAX		DisplayString(SIZE(0..15))
	MAX-ACCESS	read-write
	STATUS		current
	DESCRIPTION "Displayed Event Filter
			Oid=1.3.6.1.4.1.31968.3.1.4.1.2.77
			"
	::= { unitConfigItems 77 }

powerEvent OBJECT-TYPE
	SYNTAX		INTEGER {
		doNotLog(0),
		log(1),
		logAndSendAlert(2),
		logAndSendAlertNowNoDebounce(3)
	}
	MAX-ACCESS	read-write
	STATUS		current
	DESCRIPTION "Power Input Alarm Event, where:
			    0) 'Do Not Log'
			    1) 'Log'
			    2) 'Log & Send Alert'
			    3) 'Log & Send Alert Now (No Debounce)'
			Oid=1.3.6.1.4.1.31968.3.1.4.1.2.78
			"
	::= { unitConfigItems 78 }

trialEvent OBJECT-TYPE
	SYNTAX		INTEGER {
		doNotLog(0),
		log(1),
		logAndSendAlert(2),
		logAndSendAlertNowNoDebounce(3)
	}
	MAX-ACCESS	read-write
	STATUS		current
	DESCRIPTION "Trial Alarm Event, where:
			    0) 'Do Not Log'
			    1) 'Log'
			    2) 'Log & Send Alert'
			    3) 'Log & Send Alert Now (No Debounce)'
			Oid=1.3.6.1.4.1.31968.3.1.4.1.2.79
			"
	::= { unitConfigItems 79 }

unitTestEvent OBJECT-TYPE
	SYNTAX		INTEGER {
		doNotLog(0),
		log(1),
		logAndSendAlert(2),
		logAndSendAlertNowNoDebounce(3)
	}
	MAX-ACCESS	read-write
	STATUS		current
	DESCRIPTION "Test Active Event, where:
			    0) 'Do Not Log'
			    1) 'Log'
			    2) 'Log & Send Alert'
			    3) 'Log & Send Alert Now (No Debounce)'
			Oid=1.3.6.1.4.1.31968.3.1.4.1.2.80
			"
	::= { unitConfigItems 80 }

refEvent OBJECT-TYPE
	SYNTAX		INTEGER {
		doNotLog(0),
		log(1),
		logAndSendAlert(2),
		logAndSendAlertNowNoDebounce(3)
	}
	MAX-ACCESS	read-write
	STATUS		current
	DESCRIPTION "Reference Event, where:
			    0) 'Do Not Log'
			    1) 'Log'
			    2) 'Log & Send Alert'
			    3) 'Log & Send Alert Now (No Debounce)'
			Oid=1.3.6.1.4.1.31968.3.1.4.1.2.81
			"
	::= { unitConfigItems 81 }

monEvent OBJECT-TYPE
	SYNTAX		INTEGER {
		doNotLog(0),
		log(1),
		logAndSendAlert(2),
		logAndSendAlertNowNoDebounce(3)
	}
	MAX-ACCESS	read-write
	STATUS		current
	DESCRIPTION "Monitor Input Alarm Event, where:
			    0) 'Do Not Log'
			    1) 'Log'
			    2) 'Log & Send Alert'
			    3) 'Log & Send Alert Now (No Debounce)'
			Oid=1.3.6.1.4.1.31968.3.1.4.1.2.82
			"
	::= { unitConfigItems 82 }

redundancyEvent OBJECT-TYPE
	SYNTAX		INTEGER {
		doNotLog(0),
		log(1),
		logAndSendAlert(2),
		logAndSendAlertNowNoDebounce(3)
	}
	MAX-ACCESS	read-write
	STATUS		current
	DESCRIPTION "Redundancy Alarm Event, where:
			    0) 'Do Not Log'
			    1) 'Log'
			    2) 'Log & Send Alert'
			    3) 'Log & Send Alert Now (No Debounce)'
			Oid=1.3.6.1.4.1.31968.3.1.4.1.2.83
			"
	::= { unitConfigItems 83 }

mgmtLinkEvent OBJECT-TYPE
	SYNTAX		INTEGER {
		doNotLog(0),
		log(1),
		logAndSendAlert(2),
		logAndSendAlertNowNoDebounce(3)
	}
	MAX-ACCESS	read-write
	STATUS		current
	DESCRIPTION "Mgmt Port Event, where:
			    0) 'Do Not Log'
			    1) 'Log'
			    2) 'Log & Send Alert'
			    3) 'Log & Send Alert Now (No Debounce)'
			Oid=1.3.6.1.4.1.31968.3.1.4.1.2.84
			"
	::= { unitConfigItems 84 }

dataLinkEvent OBJECT-TYPE
	SYNTAX		INTEGER {
		doNotLog(0),
		log(1),
		logAndSendAlert(2),
		logAndSendAlertNowNoDebounce(3)
	}
	MAX-ACCESS	read-write
	STATUS		current
	DESCRIPTION "Data Port Event, where:
			    0) 'Do Not Log'
			    1) 'Log'
			    2) 'Log & Send Alert'
			    3) 'Log & Send Alert Now (No Debounce)'
			Oid=1.3.6.1.4.1.31968.3.1.4.1.2.85
			"
	::= { unitConfigItems 85 }

startupEvent OBJECT-TYPE
	SYNTAX		INTEGER {
		doNotLog(0),
		log(1),
		logAndSendAlert(2),
		logAndSendAlertNowNoDebounce(3)
	}
	MAX-ACCESS	read-write
	STATUS		current
	DESCRIPTION "Startup Event, where:
			    0) 'Do Not Log'
			    1) 'Log'
			    2) 'Log & Send Alert'
			    3) 'Log & Send Alert Now (No Debounce)'
			Oid=1.3.6.1.4.1.31968.3.1.4.1.2.86
			"
	::= { unitConfigItems 86 }

httpAccessEvent OBJECT-TYPE
	SYNTAX		INTEGER {
		doNotLog(0),
		log(1),
		logAndSendAlert(2),
		logAndSendAlertNowNoDebounce(3)
	}
	MAX-ACCESS	read-write
	STATUS		current
	DESCRIPTION "HTTP Access Event, where:
			    0) 'Do Not Log'
			    1) 'Log'
			    2) 'Log & Send Alert'
			    3) 'Log & Send Alert Now (No Debounce)'
			Oid=1.3.6.1.4.1.31968.3.1.4.1.2.87
			"
	::= { unitConfigItems 87 }

snmpAccessEvent OBJECT-TYPE
	SYNTAX		INTEGER {
		doNotLog(0),
		log(1),
		logAndSendAlert(2),
		logAndSendAlertNowNoDebounce(3)
	}
	MAX-ACCESS	read-write
	STATUS		current
	DESCRIPTION "SNMP Access Event, where:
			    0) 'Do Not Log'
			    1) 'Log'
			    2) 'Log & Send Alert'
			    3) 'Log & Send Alert Now (No Debounce)'
			Oid=1.3.6.1.4.1.31968.3.1.4.1.2.88
			"
	::= { unitConfigItems 88 }

configStoreEvent OBJECT-TYPE
	SYNTAX		INTEGER {
		doNotLog(0),
		log(1),
		logAndSendAlert(2),
		logAndSendAlertNowNoDebounce(3)
	}
	MAX-ACCESS	read-write
	STATUS		current
	DESCRIPTION "Configuration Store Event, where:
			    0) 'Do Not Log'
			    1) 'Log'
			    2) 'Log & Send Alert'
			    3) 'Log & Send Alert Now (No Debounce)'
			Oid=1.3.6.1.4.1.31968.3.1.4.1.2.89
			"
	::= { unitConfigItems 89 }

dataPortOffline OBJECT-TYPE
	SYNTAX		INTEGER {
		mute(0),
		unlink(1)
	}
	MAX-ACCESS	read-write
	STATUS		current
	DESCRIPTION "Offline Mode, where:
			    0) 'Mute'
			    1) 'Unlink'
			Oid=1.3.6.1.4.1.31968.3.1.4.1.2.90
			"
	::= { unitConfigItems 90 }

configChangeEvent OBJECT-TYPE
	SYNTAX		INTEGER {
		doNotLog(0),
		log(1),
		logAndSendAlert(2),
		logAndSendAlertNowNoDebounce(3)
	}
	MAX-ACCESS	read-write
	STATUS		current
	DESCRIPTION "Configuration Change Event, where:
			    0) 'Do Not Log'
			    1) 'Log'
			    2) 'Log & Send Alert'
			    3) 'Log & Send Alert Now (No Debounce)'
			Oid=1.3.6.1.4.1.31968.3.1.4.1.2.92
			"
	::= { unitConfigItems 92 }

unitCalibration OBJECT-TYPE
	SYNTAX		INTEGER {
		off(0),
		on(1)
	}
	MAX-ACCESS	read-write
	STATUS		current
	DESCRIPTION "Unit Calibration, where:
			    0) 'Off'
			    1) 'On'
			Oid=1.3.6.1.4.1.31968.3.1.4.1.2.93
			"
	::= { unitConfigItems 93 }

unitCalTask OBJECT-TYPE
	SYNTAX		INTEGER {
		idle(0),
		runReferenceCal(1)
	}
	MAX-ACCESS	read-write
	STATUS		current
	DESCRIPTION "Calibration Task, where:
			    0) 'Idle'
			    1) 'Run Reference Cal'
			Oid=1.3.6.1.4.1.31968.3.1.4.1.2.94
			"
	::= { unitConfigItems 94 }

storeRecallLocation OBJECT-TYPE
	SYNTAX		INTEGER {
		factory(0),
		entry01(1),
		entry02(2),
		entry03(3),
		entry04(4),
		entry05(5),
		entry06(6),
		entry07(7),
		entry08(8),
		entry09(9),
		entry10(10),
		entry11(11),
		entry12(12),
		entry13(13),
		entry14(14),
		entry15(15),
		entry16(16),
		entry17(17),
		entry18(18),
		entry19(19),
		entry20(20),
		entry21(21),
		entry22(22),
		entry23(23),
		entry24(24),
		entry25(25),
		entry26(26),
		entry27(27),
		entry28(28),
		entry29(29),
		entry30(30),
		entry31(31),
		entry32(32),
		entry33(33),
		entry34(34),
		entry35(35),
		entry36(36),
		entry37(37),
		entry38(38),
		entry39(39),
		entry40(40),
		entry41(41),
		entry42(42),
		entry43(43),
		entry44(44),
		entry45(45),
		entry46(46),
		entry47(47),
		entry48(48),
		entry49(49),
		entry50(50),
		entry51(51),
		entry52(52),
		entry53(53),
		entry54(54),
		entry55(55),
		entry56(56),
		entry57(57),
		entry58(58),
		entry59(59),
		entry60(60),
		entry61(61),
		entry62(62),
		entry63(63),
		entry64(64),
		entry65(65),
		entry66(66),
		entry67(67),
		entry68(68),
		entry69(69),
		entry70(70),
		entry71(71),
		entry72(72),
		entry73(73),
		entry74(74),
		entry75(75),
		entry76(76),
		entry77(77),
		entry78(78),
		entry79(79),
		entry80(80),
		entry81(81),
		entry82(82),
		entry83(83),
		entry84(84),
		entry85(85),
		entry86(86),
		entry87(87),
		entry88(88),
		entry89(89),
		entry90(90),
		entry91(91),
		entry92(92),
		entry93(93),
		entry94(94),
		entry95(95),
		entry96(96),
		entry97(97),
		entry98(98),
		entry99(99),
		file(100)
	}
	MAX-ACCESS	read-write
	STATUS		current
	DESCRIPTION "Storage Location, where:
			    0) 'Factory'
			    1) 'entry01'
			    2) 'entry02'
			    3) 'entry03'
			    4) 'entry04'
			    5) 'entry05'
			    6) 'entry06'
			    7) 'entry07'
			    8) 'entry08'
			    9) 'entry09'
			    10) 'entry10'
			    11) 'entry11'
			    12) 'entry12'
			    13) 'entry13'
			    14) 'entry14'
			    15) 'entry15'
			    16) 'entry16'
			    17) 'entry17'
			    18) 'entry18'
			    19) 'entry19'
			    20) 'entry20'
			    21) 'entry21'
			    22) 'entry22'
			    23) 'entry23'
			    24) 'entry24'
			    25) 'entry25'
			    26) 'entry26'
			    27) 'entry27'
			    28) 'entry28'
			    29) 'entry29'
			    30) 'entry30'
			    31) 'entry31'
			    32) 'entry32'
			    33) 'entry33'
			    34) 'entry34'
			    35) 'entry35'
			    36) 'entry36'
			    37) 'entry37'
			    38) 'entry38'
			    39) 'entry39'
			    40) 'entry40'
			    41) 'entry41'
			    42) 'entry42'
			    43) 'entry43'
			    44) 'entry44'
			    45) 'entry45'
			    46) 'entry46'
			    47) 'entry47'
			    48) 'entry48'
			    49) 'entry49'
			    50) 'entry50'
			    51) 'entry51'
			    52) 'entry52'
			    53) 'entry53'
			    54) 'entry54'
			    55) 'entry55'
			    56) 'entry56'
			    57) 'entry57'
			    58) 'entry58'
			    59) 'entry59'
			    60) 'entry60'
			    61) 'entry61'
			    62) 'entry62'
			    63) 'entry63'
			    64) 'entry64'
			    65) 'entry65'
			    66) 'entry66'
			    67) 'entry67'
			    68) 'entry68'
			    69) 'entry69'
			    70) 'entry70'
			    71) 'entry71'
			    72) 'entry72'
			    73) 'entry73'
			    74) 'entry74'
			    75) 'entry75'
			    76) 'entry76'
			    77) 'entry77'
			    78) 'entry78'
			    79) 'entry79'
			    80) 'entry80'
			    81) 'entry81'
			    82) 'entry82'
			    83) 'entry83'
			    84) 'entry84'
			    85) 'entry85'
			    86) 'entry86'
			    87) 'entry87'
			    88) 'entry88'
			    89) 'entry89'
			    90) 'entry90'
			    91) 'entry91'
			    92) 'entry92'
			    93) 'entry93'
			    94) 'entry94'
			    95) 'entry95'
			    96) 'entry96'
			    97) 'entry97'
			    98) 'entry98'
			    99) 'entry99'
			    100) 'File'
			Oid=1.3.6.1.4.1.31968.3.1.4.1.2.95
			"
	::= { unitConfigItems 95 }

storeRecallDescription OBJECT-TYPE
	SYNTAX		DisplayString(SIZE(0..80))
	MAX-ACCESS	read-write
	STATUS		current
	DESCRIPTION "Store Name
			Oid=1.3.6.1.4.1.31968.3.1.4.1.2.96
			"
	::= { unitConfigItems 96 }

storeRecallOperation OBJECT-TYPE
	SYNTAX		INTEGER {
		idle(0),
		recallAll(1),
		recallUnitOnly(2),
		recallTxAndRxOnly(3),
		recallTxOnly(4),
		recallRxOnly(5),
		store(10),
		delete(20)
	}
	MAX-ACCESS	read-write
	STATUS		current
	DESCRIPTION "Storage Operation, where:
			    0) 'Idle'
			    1) 'Recall All'
			    2) 'Recall Unit Only'
			    3) 'Recall Tx & Rx Only'
			    4) 'Recall Tx Only'
			    5) 'Recall Rx Only'
			    10) 'Store'
			    20) 'Delete'
			Oid=1.3.6.1.4.1.31968.3.1.4.1.2.97
			"
	::= { unitConfigItems 97 }

autoRestore OBJECT-TYPE
	SYNTAX		INTEGER {
		off(0),
		restoreAll(1),
		restoreUnitOnly(2),
		restoreTxAndRxOnly(3),
		restoreTxOnly(4),
		restoreRxOnly(5)
	}
	MAX-ACCESS	read-write
	STATUS		current
	DESCRIPTION "Auto Restore, where:
			    0) 'Off'
			    1) 'Restore All'
			    2) 'Restore Unit Only'
			    3) 'Restore Tx & Rx Only'
			    4) 'Restore Tx Only'
			    5) 'Restore Rx Only'
			Oid=1.3.6.1.4.1.31968.3.1.4.1.2.98
			"
	::= { unitConfigItems 98 }

autoRestoreAfter OBJECT-TYPE
	SYNTAX		Unsigned32
	UNITS		"s"
	MAX-ACCESS	read-write
	STATUS		current
	DESCRIPTION "Auto Restore After
			Oid=1.3.6.1.4.1.31968.3.1.4.1.2.99
			"
	::= { unitConfigItems 99 }

autoRestoreLocation OBJECT-TYPE
	SYNTAX		INTEGER {
		entry01(1),
		entry02(2),
		entry03(3),
		entry04(4),
		entry05(5),
		entry06(6),
		entry07(7),
		entry08(8),
		entry09(9),
		entry10(10),
		entry11(11),
		entry12(12),
		entry13(13),
		entry14(14),
		entry15(15),
		entry16(16),
		entry17(17),
		entry18(18),
		entry19(19),
		entry20(20),
		entry21(21),
		entry22(22),
		entry23(23),
		entry24(24),
		entry25(25),
		entry26(26),
		entry27(27),
		entry28(28),
		entry29(29),
		entry30(30),
		entry31(31),
		entry32(32),
		entry33(33),
		entry34(34),
		entry35(35),
		entry36(36),
		entry37(37),
		entry38(38),
		entry39(39),
		entry40(40),
		entry41(41),
		entry42(42),
		entry43(43),
		entry44(44),
		entry45(45),
		entry46(46),
		entry47(47),
		entry48(48),
		entry49(49),
		entry50(50),
		entry51(51),
		entry52(52),
		entry53(53),
		entry54(54),
		entry55(55),
		entry56(56),
		entry57(57),
		entry58(58),
		entry59(59),
		entry60(60),
		entry61(61),
		entry62(62),
		entry63(63),
		entry64(64),
		entry65(65),
		entry66(66),
		entry67(67),
		entry68(68),
		entry69(69),
		entry70(70),
		entry71(71),
		entry72(72),
		entry73(73),
		entry74(74),
		entry75(75),
		entry76(76),
		entry77(77),
		entry78(78),
		entry79(79),
		entry80(80),
		entry81(81),
		entry82(82),
		entry83(83),
		entry84(84),
		entry85(85),
		entry86(86),
		entry87(87),
		entry88(88),
		entry89(89),
		entry90(90),
		entry91(91),
		entry92(92),
		entry93(93),
		entry94(94),
		entry95(95),
		entry96(96),
		entry97(97),
		entry98(98),
		entry99(99)
	}
	MAX-ACCESS	read-write
	STATUS		current
	DESCRIPTION "Auto Restore Location, where:
			    1) 'entry01'
			    2) 'entry02'
			    3) 'entry03'
			    4) 'entry04'
			    5) 'entry05'
			    6) 'entry06'
			    7) 'entry07'
			    8) 'entry08'
			    9) 'entry09'
			    10) 'entry10'
			    11) 'entry11'
			    12) 'entry12'
			    13) 'entry13'
			    14) 'entry14'
			    15) 'entry15'
			    16) 'entry16'
			    17) 'entry17'
			    18) 'entry18'
			    19) 'entry19'
			    20) 'entry20'
			    21) 'entry21'
			    22) 'entry22'
			    23) 'entry23'
			    24) 'entry24'
			    25) 'entry25'
			    26) 'entry26'
			    27) 'entry27'
			    28) 'entry28'
			    29) 'entry29'
			    30) 'entry30'
			    31) 'entry31'
			    32) 'entry32'
			    33) 'entry33'
			    34) 'entry34'
			    35) 'entry35'
			    36) 'entry36'
			    37) 'entry37'
			    38) 'entry38'
			    39) 'entry39'
			    40) 'entry40'
			    41) 'entry41'
			    42) 'entry42'
			    43) 'entry43'
			    44) 'entry44'
			    45) 'entry45'
			    46) 'entry46'
			    47) 'entry47'
			    48) 'entry48'
			    49) 'entry49'
			    50) 'entry50'
			    51) 'entry51'
			    52) 'entry52'
			    53) 'entry53'
			    54) 'entry54'
			    55) 'entry55'
			    56) 'entry56'
			    57) 'entry57'
			    58) 'entry58'
			    59) 'entry59'
			    60) 'entry60'
			    61) 'entry61'
			    62) 'entry62'
			    63) 'entry63'
			    64) 'entry64'
			    65) 'entry65'
			    66) 'entry66'
			    67) 'entry67'
			    68) 'entry68'
			    69) 'entry69'
			    70) 'entry70'
			    71) 'entry71'
			    72) 'entry72'
			    73) 'entry73'
			    74) 'entry74'
			    75) 'entry75'
			    76) 'entry76'
			    77) 'entry77'
			    78) 'entry78'
			    79) 'entry79'
			    80) 'entry80'
			    81) 'entry81'
			    82) 'entry82'
			    83) 'entry83'
			    84) 'entry84'
			    85) 'entry85'
			    86) 'entry86'
			    87) 'entry87'
			    88) 'entry88'
			    89) 'entry89'
			    90) 'entry90'
			    91) 'entry91'
			    92) 'entry92'
			    93) 'entry93'
			    94) 'entry94'
			    95) 'entry95'
			    96) 'entry96'
			    97) 'entry97'
			    98) 'entry98'
			    99) 'entry99'
			Oid=1.3.6.1.4.1.31968.3.1.4.1.2.100
			"
	::= { unitConfigItems 100 }

configStartup OBJECT-TYPE
	SYNTAX		INTEGER {
		lastState(0),
		entry01(1),
		entry02(2),
		entry03(3),
		entry04(4),
		entry05(5),
		entry06(6),
		entry07(7),
		entry08(8),
		entry09(9),
		entry10(10),
		entry11(11),
		entry12(12),
		entry13(13),
		entry14(14),
		entry15(15),
		entry16(16),
		entry17(17),
		entry18(18),
		entry19(19),
		entry20(20),
		entry21(21),
		entry22(22),
		entry23(23),
		entry24(24),
		entry25(25),
		entry26(26),
		entry27(27),
		entry28(28),
		entry29(29),
		entry30(30),
		entry31(31),
		entry32(32),
		entry33(33),
		entry34(34),
		entry35(35),
		entry36(36),
		entry37(37),
		entry38(38),
		entry39(39),
		entry40(40),
		entry41(41),
		entry42(42),
		entry43(43),
		entry44(44),
		entry45(45),
		entry46(46),
		entry47(47),
		entry48(48),
		entry49(49),
		entry50(50),
		entry51(51),
		entry52(52),
		entry53(53),
		entry54(54),
		entry55(55),
		entry56(56),
		entry57(57),
		entry58(58),
		entry59(59),
		entry60(60),
		entry61(61),
		entry62(62),
		entry63(63),
		entry64(64),
		entry65(65),
		entry66(66),
		entry67(67),
		entry68(68),
		entry69(69),
		entry70(70),
		entry71(71),
		entry72(72),
		entry73(73),
		entry74(74),
		entry75(75),
		entry76(76),
		entry77(77),
		entry78(78),
		entry79(79),
		entry80(80),
		entry81(81),
		entry82(82),
		entry83(83),
		entry84(84),
		entry85(85),
		entry86(86),
		entry87(87),
		entry88(88),
		entry89(89),
		entry90(90),
		entry91(91),
		entry92(92),
		entry93(93),
		entry94(94),
		entry95(95),
		entry96(96),
		entry97(97),
		entry98(98),
		entry99(99)
	}
	MAX-ACCESS	read-write
	STATUS		current
	DESCRIPTION "Configuration On Start Up, where:
			    0) 'Last State'
			    1) 'entry01'
			    2) 'entry02'
			    3) 'entry03'
			    4) 'entry04'
			    5) 'entry05'
			    6) 'entry06'
			    7) 'entry07'
			    8) 'entry08'
			    9) 'entry09'
			    10) 'entry10'
			    11) 'entry11'
			    12) 'entry12'
			    13) 'entry13'
			    14) 'entry14'
			    15) 'entry15'
			    16) 'entry16'
			    17) 'entry17'
			    18) 'entry18'
			    19) 'entry19'
			    20) 'entry20'
			    21) 'entry21'
			    22) 'entry22'
			    23) 'entry23'
			    24) 'entry24'
			    25) 'entry25'
			    26) 'entry26'
			    27) 'entry27'
			    28) 'entry28'
			    29) 'entry29'
			    30) 'entry30'
			    31) 'entry31'
			    32) 'entry32'
			    33) 'entry33'
			    34) 'entry34'
			    35) 'entry35'
			    36) 'entry36'
			    37) 'entry37'
			    38) 'entry38'
			    39) 'entry39'
			    40) 'entry40'
			    41) 'entry41'
			    42) 'entry42'
			    43) 'entry43'
			    44) 'entry44'
			    45) 'entry45'
			    46) 'entry46'
			    47) 'entry47'
			    48) 'entry48'
			    49) 'entry49'
			    50) 'entry50'
			    51) 'entry51'
			    52) 'entry52'
			    53) 'entry53'
			    54) 'entry54'
			    55) 'entry55'
			    56) 'entry56'
			    57) 'entry57'
			    58) 'entry58'
			    59) 'entry59'
			    60) 'entry60'
			    61) 'entry61'
			    62) 'entry62'
			    63) 'entry63'
			    64) 'entry64'
			    65) 'entry65'
			    66) 'entry66'
			    67) 'entry67'
			    68) 'entry68'
			    69) 'entry69'
			    70) 'entry70'
			    71) 'entry71'
			    72) 'entry72'
			    73) 'entry73'
			    74) 'entry74'
			    75) 'entry75'
			    76) 'entry76'
			    77) 'entry77'
			    78) 'entry78'
			    79) 'entry79'
			    80) 'entry80'
			    81) 'entry81'
			    82) 'entry82'
			    83) 'entry83'
			    84) 'entry84'
			    85) 'entry85'
			    86) 'entry86'
			    87) 'entry87'
			    88) 'entry88'
			    89) 'entry89'
			    90) 'entry90'
			    91) 'entry91'
			    92) 'entry92'
			    93) 'entry93'
			    94) 'entry94'
			    95) 'entry95'
			    96) 'entry96'
			    97) 'entry97'
			    98) 'entry98'
			    99) 'entry99'
			Oid=1.3.6.1.4.1.31968.3.1.4.1.2.101
			"
	::= { unitConfigItems 101 }

satId OBJECT-TYPE
	SYNTAX		DisplayString(SIZE(0..28))
	MAX-ACCESS	read-write
	STATUS		current
	DESCRIPTION "Satellite ID
			Oid=1.3.6.1.4.1.31968.3.1.4.1.2.102
			"
	::= { unitConfigItems 102 }

beamId OBJECT-TYPE
	SYNTAX		Unsigned32
	UNITS		"1"
	MAX-ACCESS	read-write
	STATUS		current
	DESCRIPTION "Beam ID
			Oid=1.3.6.1.4.1.31968.3.1.4.1.2.103
			"
	::= { unitConfigItems 103 }

mgmtVlanId OBJECT-TYPE
	SYNTAX		Unsigned32
	UNITS		"1"
	MAX-ACCESS	read-write
	STATUS		current
	DESCRIPTION "VLAN ID,
			    0=None
			Oid=1.3.6.1.4.1.31968.3.1.4.1.2.104
			"
	::= { unitConfigItems 104 }

mgmtMccBridge OBJECT-TYPE
	SYNTAX		INTEGER {
		off(0),
		on(1)
	}
	MAX-ACCESS	read-write
	STATUS		current
	DESCRIPTION "MCC Bridge, where:
			    0) 'Off'
			    1) 'On'
			Oid=1.3.6.1.4.1.31968.3.1.4.1.2.105
			"
	::= { unitConfigItems 105 }

mgmtFilter OBJECT-TYPE
	SYNTAX		INTEGER {
		off(0),
		on(1)
	}
	MAX-ACCESS	read-write
	STATUS		current
	DESCRIPTION "Bridge IP Filter, where:
			    0) 'Off'
			    1) 'On'
			Oid=1.3.6.1.4.1.31968.3.1.4.1.2.106
			"
	::= { unitConfigItems 106 }

mgmtFilterRangeStart OBJECT-TYPE
	SYNTAX		IpAddress
	MAX-ACCESS	read-write
	STATUS		current
	DESCRIPTION "Bridge IP Address Range Start
			Oid=1.3.6.1.4.1.31968.3.1.4.1.2.107
			"
	::= { unitConfigItems 107 }

mgmtFilterRangeEnd OBJECT-TYPE
	SYNTAX		IpAddress
	MAX-ACCESS	read-write
	STATUS		current
	DESCRIPTION "Bridge IP Address Range End
			Oid=1.3.6.1.4.1.31968.3.1.4.1.2.108
			"
	::= { unitConfigItems 108 }

mgmtIngressVlanFilter OBJECT-TYPE
	SYNTAX		INTEGER {
		passMatchStripTag(0),
		passMatchAppendTag(1),
		passMatchPassTag(2),
		passRangeMatchPassTag(3)
	}
	MAX-ACCESS	read-write
	STATUS		current
	DESCRIPTION "Ingress VLAN Tag Filter, where:
			    0) 'Pass Match, Strip Tag'
			    1) 'Pass Match, Append Tag'
			    2) 'Pass Match, Pass Tag'
			    3) 'Pass Range Match, Pass Tag'
			Oid=1.3.6.1.4.1.31968.3.1.4.1.2.109
			"
	::= { unitConfigItems 109 }

mgmtEgressVlanFilter OBJECT-TYPE
	SYNTAX		INTEGER {
		passMatchAppendTag(0),
		passMatchStripTag(1),
		passMatchPassTag(2),
		passRangeMatchPassTag(3)
	}
	MAX-ACCESS	read-only
	STATUS		current
	DESCRIPTION "Egress VLAN Tag Filter, where:
			    0) 'Pass Match, Append Tag'
			    1) 'Pass Match, Strip Tag'
			    2) 'Pass Match, Pass Tag'
			    3) 'Pass Range Match, Pass Tag'
			Oid=1.3.6.1.4.1.31968.3.1.4.1.2.110
			"
	::= { unitConfigItems 110 }

mgmtVlanFilterTagStart OBJECT-TYPE
	SYNTAX		Unsigned32
	UNITS		"1"
	MAX-ACCESS	read-write
	STATUS		current
	DESCRIPTION "Bridge VLAN Tag Range Start
			Oid=1.3.6.1.4.1.31968.3.1.4.1.2.111
			"
	::= { unitConfigItems 111 }

mgmtVlanFilterTagEnd OBJECT-TYPE
	SYNTAX		Unsigned32
	UNITS		"1"
	MAX-ACCESS	read-write
	STATUS		current
	DESCRIPTION "Bridge VLAN Tag Range End
			Oid=1.3.6.1.4.1.31968.3.1.4.1.2.112
			"
	::= { unitConfigItems 112 }

dataIngressVlanFilter OBJECT-TYPE
	SYNTAX		INTEGER {
		off(0),
		passMatchStripTag(1),
		passAppendTag(2),
		passMatchPassTag(3),
		passRangeMatchPassTag(4)
	}
	MAX-ACCESS	read-write
	STATUS		current
	DESCRIPTION "Ingress VLAN Tag Filter, where:
			    0) 'Off'
			    1) 'Pass Match, Strip Tag'
			    2) 'Pass, Append Tag'
			    3) 'Pass Match, Pass Tag'
			    4) 'Pass Range Match, Pass Tag'
			Oid=1.3.6.1.4.1.31968.3.1.4.1.2.113
			"
	::= { unitConfigItems 113 }

dataEgressVlanFilter OBJECT-TYPE
	SYNTAX		INTEGER {
		off(0),
		passAppendTag(1),
		passMatchStripTag(2),
		passMatchPassTag(3),
		passRangeMatchPassTag(4),
		passAppendTxHubTag(5)
	}
	MAX-ACCESS	read-write
	STATUS		current
	DESCRIPTION "Egress VLAN Tag Filter, where:
			    0) 'Off'
			    1) 'Pass, Append Tag'
			    2) 'Pass Match, Strip Tag'
			    3) 'Pass Match, Pass Tag'
			    4) 'Pass Range Match, Pass Tag'
			    5) 'Pass, Append Tx Hub Tag'
			Oid=1.3.6.1.4.1.31968.3.1.4.1.2.114
			"
	::= { unitConfigItems 114 }

dataVlanFilterId OBJECT-TYPE
	SYNTAX		Unsigned32
	UNITS		"1"
	MAX-ACCESS	read-write
	STATUS		current
	DESCRIPTION "VLAN ID
			Oid=1.3.6.1.4.1.31968.3.1.4.1.2.115
			"
	::= { unitConfigItems 115 }

dataVlanFilterTagStart OBJECT-TYPE
	SYNTAX		Unsigned32
	UNITS		"1"
	MAX-ACCESS	read-write
	STATUS		current
	DESCRIPTION "VLAN Tag Range Start
			Oid=1.3.6.1.4.1.31968.3.1.4.1.2.116
			"
	::= { unitConfigItems 116 }

dataVlanFilterTagEnd OBJECT-TYPE
	SYNTAX		Unsigned32
	UNITS		"1"
	MAX-ACCESS	read-write
	STATUS		current
	DESCRIPTION "VLAN Tag Range End
			Oid=1.3.6.1.4.1.31968.3.1.4.1.2.117
			"
	::= { unitConfigItems 117 }

dataEchoFilter OBJECT-TYPE
	SYNTAX		INTEGER {
		off(0),
		learnTxFilterRx(1)
	}
	MAX-ACCESS	read-write
	STATUS		current
	DESCRIPTION "Echo Filter, where:
			    0) 'Off'
			    1) 'Learn Tx, Filter Rx'
			Oid=1.3.6.1.4.1.31968.3.1.4.1.2.118
			"
	::= { unitConfigItems 118 }

eventClear OBJECT-TYPE
	SYNTAX		INTEGER {
		logRunning(0),
		logClearSelfClearing(1)
	}
	MAX-ACCESS	read-write
	STATUS		current
	DESCRIPTION "Event Log Clear, where:
			    0) 'Log Running...'
			    1) 'Log Clear - Self Clearing'
			Oid=1.3.6.1.4.1.31968.3.1.4.1.2.119
			"
	::= { unitConfigItems 119 }

configRestoreEvent OBJECT-TYPE
	SYNTAX		INTEGER {
		doNotLog(0),
		log(1),
		logAndSendAlert(2),
		logAndSendAlertNowNoDebounce(3)
	}
	MAX-ACCESS	read-write
	STATUS		current
	DESCRIPTION "Configuration Restore Event, where:
			    0) 'Do Not Log'
			    1) 'Log'
			    2) 'Log & Send Alert'
			    3) 'Log & Send Alert Now (No Debounce)'
			Oid=1.3.6.1.4.1.31968.3.1.4.1.2.120
			"
	::= { unitConfigItems 120 }

systemEvent OBJECT-TYPE
	SYNTAX		INTEGER {
		log(1),
		logAndSendAlert(2),
		logAndSendAlertNowNoDebounce(3)
	}
	MAX-ACCESS	read-write
	STATUS		current
	DESCRIPTION "System Event, where:
			    1) 'Log'
			    2) 'Log & Send Alert'
			    3) 'Log & Send Alert Now (No Debounce)'
			Oid=1.3.6.1.4.1.31968.3.1.4.1.2.121
			"
	::= { unitConfigItems 121 }

timeEvent OBJECT-TYPE
	SYNTAX		INTEGER {
		doNotLog(0),
		log(1),
		logAndSendAlert(2),
		logAndSendAlertNowNoDebounce(3)
	}
	MAX-ACCESS	read-write
	STATUS		current
	DESCRIPTION "Time Event, where:
			    0) 'Do Not Log'
			    1) 'Log'
			    2) 'Log & Send Alert'
			    3) 'Log & Send Alert Now (No Debounce)'
			Oid=1.3.6.1.4.1.31968.3.1.4.1.2.122
			"
	::= { unitConfigItems 122 }

autoRestoreWhen OBJECT-TYPE
	SYNTAX		INTEGER {
		anyRxUnlocked(0),
		allRxUnlocked(1),
		rx1Unlocked(2),
		rx2Unlocked(3),
		rx3Unlocked(4),
		rx4Unlocked(5),
		rx5Unlocked(6),
		rx6Unlocked(7),
		rx7Unlocked(8),
		rx8Unlocked(9),
		rx9Unlocked(10),
		rx10Unlocked(11),
		rx11Unlocked(12),
		rx12Unlocked(13),
		rx13Unlocked(14),
		rx14Unlocked(15),
		rx15Unlocked(16),
		rx16Unlocked(17)
	}
	MAX-ACCESS	read-write
	STATUS		current
	DESCRIPTION "Auto Restore When, where:
			    0) 'Any Rx Unlocked'
			    1) 'All Rx Unlocked'
			    2) 'Rx 1 Unlocked'
			    3) 'Rx 2 Unlocked'
			    4) 'Rx 3 Unlocked'
			    5) 'Rx 4 Unlocked'
			    6) 'Rx 5 Unlocked'
			    7) 'Rx 6 Unlocked'
			    8) 'Rx 7 Unlocked'
			    9) 'Rx 8 Unlocked'
			    10) 'Rx 9 Unlocked'
			    11) 'Rx 10 Unlocked'
			    12) 'Rx 11 Unlocked'
			    13) 'Rx 12 Unlocked'
			    14) 'Rx 13 Unlocked'
			    15) 'Rx 14 Unlocked'
			    16) 'Rx 15 Unlocked'
			    17) 'Rx 16 Unlocked'
			Oid=1.3.6.1.4.1.31968.3.1.4.1.2.123
			"
	::= { unitConfigItems 123 }

satFind OBJECT-TYPE
	SYNTAX		Unsigned32
	UNITS		"1"
	MAX-ACCESS	read-write
	STATUS		current
	DESCRIPTION "Find Catalog Number
			Oid=1.3.6.1.4.1.31968.3.1.4.1.2.124
			"
	::= { unitConfigItems 124 }

satSearchOperation OBJECT-TYPE
	SYNTAX		INTEGER {
		idle(0),
		notFound(1),
		foundBadEntry(2),
		found(3),
		setTleOrbitalElements(4)
	}
	MAX-ACCESS	read-write
	STATUS		current
	DESCRIPTION "Search Operation, where:
			    0) 'Idle'
			    1) 'NOT FOUND'
			    2) 'FOUND, BAD ENTRY'
			    3) 'Found'
			    4) 'Set TLE Orbital Elements'
			Oid=1.3.6.1.4.1.31968.3.1.4.1.2.125
			"
	::= { unitConfigItems 125 }

satTle OBJECT-TYPE
	SYNTAX		DisplayString(SIZE(0..170))
	MAX-ACCESS	read-write
	STATUS		current
	DESCRIPTION "TLE Orbital Elements
			Oid=1.3.6.1.4.1.31968.3.1.4.1.2.126
			"
	::= { unitConfigItems 126 }

batteryAlarm OBJECT-TYPE
	SYNTAX		INTEGER {
		off(0),
		report(1),
		alarm(3),
		alarmAndRelayOutput(5)
	}
	MAX-ACCESS	read-write
	STATUS		current
	DESCRIPTION "RTC Battery Alarm, where:
			    0) 'Off'
			    1) 'Report'
			    3) 'Alarm'
			    5) 'Alarm & Relay Output'
			Oid=1.3.6.1.4.1.31968.3.1.4.1.2.127
			"
	::= { unitConfigItems 127 }

snmpReadAuthEncryption OBJECT-TYPE
	SYNTAX		INTEGER {
		none(0),
		md5(1),
		sha1(2),
		sha2224(3),
		sha2256(4),
		sha2384(5),
		sha2512(6)
	}
	MAX-ACCESS	read-write
	STATUS		current
	DESCRIPTION "Read Only Auth Encryption, where:
			    0) 'None'
			    1) 'MD5'
			    2) 'SHA1'
			    3) 'SHA2-224'
			    4) 'SHA2-256'
			    5) 'SHA2-384'
			    6) 'SHA2-512'
			Oid=1.3.6.1.4.1.31968.3.1.4.1.2.129
			"
	::= { unitConfigItems 129 }

snmpReadPrivEncryption OBJECT-TYPE
	SYNTAX		INTEGER {
		none(0),
		des(1),
		aes128(2)
	}
	MAX-ACCESS	read-write
	STATUS		current
	DESCRIPTION "Read Only Priv Encryption, where:
			    0) 'None'
			    1) 'DES'
			    2) 'AES-128'
			Oid=1.3.6.1.4.1.31968.3.1.4.1.2.130
			"
	::= { unitConfigItems 130 }

snmpFullAuthEncryption OBJECT-TYPE
	SYNTAX		INTEGER {
		none(0),
		md5(1),
		sha1(2),
		sha2224(3),
		sha2256(4),
		sha2384(5),
		sha2512(6)
	}
	MAX-ACCESS	read-write
	STATUS		current
	DESCRIPTION "Read/Write Auth Encryption, where:
			    0) 'None'
			    1) 'MD5'
			    2) 'SHA1'
			    3) 'SHA2-224'
			    4) 'SHA2-256'
			    5) 'SHA2-384'
			    6) 'SHA2-512'
			Oid=1.3.6.1.4.1.31968.3.1.4.1.2.131
			"
	::= { unitConfigItems 131 }

snmpFullPrivEncryption OBJECT-TYPE
	SYNTAX		INTEGER {
		none(0),
		des(1),
		aes128(2)
	}
	MAX-ACCESS	read-write
	STATUS		current
	DESCRIPTION "Read/Write Priv Encryption, where:
			    0) 'None'
			    1) 'DES'
			    2) 'AES-128'
			Oid=1.3.6.1.4.1.31968.3.1.4.1.2.132
			"
	::= { unitConfigItems 132 }

snmpReadUsername OBJECT-TYPE
	SYNTAX		DisplayString(SIZE(8..32))
	MAX-ACCESS	read-write
	STATUS		current
	DESCRIPTION "Read Only Username
			Oid=1.3.6.1.4.1.31968.3.1.4.1.2.133
			"
	::= { unitConfigItems 133 }

snmpReadAuthPassword OBJECT-TYPE
	SYNTAX		DisplayString(SIZE(8..64))
	MAX-ACCESS	read-write
	STATUS		current
	DESCRIPTION "Read Only Auth Password
			Oid=1.3.6.1.4.1.31968.3.1.4.1.2.134
			"
	::= { unitConfigItems 134 }

snmpReadPrivPassword OBJECT-TYPE
	SYNTAX		DisplayString(SIZE(8..64))
	MAX-ACCESS	read-write
	STATUS		current
	DESCRIPTION "Read Only Priv Password
			Oid=1.3.6.1.4.1.31968.3.1.4.1.2.135
			"
	::= { unitConfigItems 135 }

snmpFullUsername OBJECT-TYPE
	SYNTAX		DisplayString(SIZE(8..32))
	MAX-ACCESS	read-write
	STATUS		current
	DESCRIPTION "Read/Write Username
			Oid=1.3.6.1.4.1.31968.3.1.4.1.2.136
			"
	::= { unitConfigItems 136 }

snmpFullAuthPassword OBJECT-TYPE
	SYNTAX		DisplayString(SIZE(8..64))
	MAX-ACCESS	read-write
	STATUS		current
	DESCRIPTION "Read/Write Auth Password
			Oid=1.3.6.1.4.1.31968.3.1.4.1.2.137
			"
	::= { unitConfigItems 137 }

snmpFullPrivPassword OBJECT-TYPE
	SYNTAX		DisplayString(SIZE(8..64))
	MAX-ACCESS	read-write
	STATUS		current
	DESCRIPTION "Read/Write Priv Password
			Oid=1.3.6.1.4.1.31968.3.1.4.1.2.138
			"
	::= { unitConfigItems 138 }

snmpAlertProtocol OBJECT-TYPE
	SYNTAX		INTEGER {
		v1(0),
		v2c(1),
		v3(2)
	}
	MAX-ACCESS	read-write
	STATUS		current
	DESCRIPTION "Alert Protocol, where:
			    0) 'V1'
			    1) 'V2c'
			    2) 'V3'
			Oid=1.3.6.1.4.1.31968.3.1.4.1.2.139
			"
	::= { unitConfigItems 139 }

snmpAlertAuthEncryption OBJECT-TYPE
	SYNTAX		INTEGER {
		none(0),
		md5(1),
		sha1(2),
		sha2224(3),
		sha2256(4),
		sha2384(5),
		sha2512(6)
	}
	MAX-ACCESS	read-write
	STATUS		current
	DESCRIPTION "Alert Auth Encryption, where:
			    0) 'None'
			    1) 'MD5'
			    2) 'SHA1'
			    3) 'SHA2-224'
			    4) 'SHA2-256'
			    5) 'SHA2-384'
			    6) 'SHA2-512'
			Oid=1.3.6.1.4.1.31968.3.1.4.1.2.140
			"
	::= { unitConfigItems 140 }

snmpAlertPrivEncryption OBJECT-TYPE
	SYNTAX		INTEGER {
		none(0),
		des(1),
		aes128(2)
	}
	MAX-ACCESS	read-write
	STATUS		current
	DESCRIPTION "Alert Priv Encryption, where:
			    0) 'None'
			    1) 'DES'
			    2) 'AES-128'
			Oid=1.3.6.1.4.1.31968.3.1.4.1.2.141
			"
	::= { unitConfigItems 141 }

snmpAlertUsername OBJECT-TYPE
	SYNTAX		DisplayString(SIZE(8..32))
	MAX-ACCESS	read-write
	STATUS		current
	DESCRIPTION "Alert Username
			Oid=1.3.6.1.4.1.31968.3.1.4.1.2.142
			"
	::= { unitConfigItems 142 }

snmpAlertAuthPassword OBJECT-TYPE
	SYNTAX		DisplayString(SIZE(8..64))
	MAX-ACCESS	read-write
	STATUS		current
	DESCRIPTION "Alert Auth Password
			Oid=1.3.6.1.4.1.31968.3.1.4.1.2.143
			"
	::= { unitConfigItems 143 }

snmpAlertPrivPassword OBJECT-TYPE
	SYNTAX		DisplayString(SIZE(8..64))
	MAX-ACCESS	read-write
	STATUS		current
	DESCRIPTION "Alert Priv Password
			Oid=1.3.6.1.4.1.31968.3.1.4.1.2.144
			"
	::= { unitConfigItems 144 }

batteryEvent OBJECT-TYPE
	SYNTAX		INTEGER {
		doNotLog(0),
		log(1),
		logAndSendAlert(2),
		logAndSendAlertNow(3)
	}
	MAX-ACCESS	read-write
	STATUS		current
	DESCRIPTION "RTC Battery Event, where:
			    0) 'Do Not Log'
			    1) 'Log'
			    2) 'Log & Send Alert'
			    3) 'Log & Send Alert Now'
			Oid=1.3.6.1.4.1.31968.3.1.4.1.2.146
			"
	::= { unitConfigItems 146 }

dataPortLink OBJECT-TYPE
	SYNTAX		INTEGER {
		auto(0),
		n10Mb(1),
		n100Mb(2),
		n1Gb(3)
	}
	MAX-ACCESS	read-write
	STATUS		current
	DESCRIPTION "Data Port Link, where:
			    0) 'Auto'
			    1) '10 Mb'
			    2) '100 Mb'
			    3) '1 Gb'
			Oid=1.3.6.1.4.1.31968.3.1.4.1.2.147
			"
	::= { unitConfigItems 147 }

acuOperation OBJECT-TYPE
	SYNTAX		INTEGER {
		off(0),
		on(1),
		onStartWithSatelliteFind(2)
	}
	MAX-ACCESS	read-write
	STATUS		current
	DESCRIPTION "Operation, where:
			    0) 'Off'
			    1) 'On'
			    2) 'On, Start With Satellite Find'
			Oid=1.3.6.1.4.1.31968.3.1.4.1.2.148
			"
	::= { unitConfigItems 148 }

acuIpProtocol OBJECT-TYPE
	SYNTAX		INTEGER {
		tcp(0),
		udp(1)
	}
	MAX-ACCESS	read-write
	STATUS		current
	DESCRIPTION "IP Protocol, where:
			    0) 'TCP'
			    1) 'UDP'
			Oid=1.3.6.1.4.1.31968.3.1.4.1.2.149
			"
	::= { unitConfigItems 149 }

acuAddr OBJECT-TYPE
	SYNTAX		IpAddress
	MAX-ACCESS	read-write
	STATUS		current
	DESCRIPTION "IP Address
			Oid=1.3.6.1.4.1.31968.3.1.4.1.2.150
			"
	::= { unitConfigItems 150 }

acuPort OBJECT-TYPE
	SYNTAX		Unsigned32
	UNITS		"1"
	MAX-ACCESS	read-write
	STATUS		current
	DESCRIPTION "IP Port
			Oid=1.3.6.1.4.1.31968.3.1.4.1.2.151
			"
	::= { unitConfigItems 151 }

acuVersion OBJECT-TYPE
	SYNTAX		INTEGER {
		n112(0),
		n116(1),
		n117(2)
	}
	MAX-ACCESS	read-write
	STATUS		current
	DESCRIPTION "OpenAMIP Version, where:
			    0) '1.12'
			    1) '1.16'
			    2) '1.17'
			Oid=1.3.6.1.4.1.31968.3.1.4.1.2.152
			"
	::= { unitConfigItems 152 }

acuAliveInterval OBJECT-TYPE
	SYNTAX		Unsigned32
	UNITS		"s"
	MAX-ACCESS	read-write
	STATUS		current
	DESCRIPTION "Keepalive Interval
			Oid=1.3.6.1.4.1.31968.3.1.4.1.2.153
			"
	::= { unitConfigItems 153 }

acuLocationInterval OBJECT-TYPE
	SYNTAX		Unsigned32
	UNITS		"s"
	MAX-ACCESS	read-write
	STATUS		current
	DESCRIPTION "Location Interval
			Oid=1.3.6.1.4.1.31968.3.1.4.1.2.154
			"
	::= { unitConfigItems 154 }

acuTxPolarization OBJECT-TYPE
	SYNTAX		INTEGER {
		leftHandCircular(0),
		rightHandCircular(1),
		vertical(2),
		horizontal(3)
	}
	MAX-ACCESS	read-write
	STATUS		current
	DESCRIPTION "Tx Polarization, where:
			    0) 'Left-Hand Circular'
			    1) 'Right-Hand Circular'
			    2) 'Vertical'
			    3) 'Horizontal'
			Oid=1.3.6.1.4.1.31968.3.1.4.1.2.155
			"
	::= { unitConfigItems 155 }

acuRxPolarization OBJECT-TYPE
	SYNTAX		INTEGER {
		leftHandCircular(0),
		rightHandCircular(1),
		vertical(2),
		horizontal(3)
	}
	MAX-ACCESS	read-write
	STATUS		current
	DESCRIPTION "Rx Polarization, where:
			    0) 'Left-Hand Circular'
			    1) 'Right-Hand Circular'
			    2) 'Vertical'
			    3) 'Horizontal'
			Oid=1.3.6.1.4.1.31968.3.1.4.1.2.156
			"
	::= { unitConfigItems 156 }

acuMinSkew OBJECT-TYPE
	SYNTAX		Unsigned32
	UNITS		"0.001 Degree"
	MAX-ACCESS	read-write
	STATUS		current
	DESCRIPTION "Min Skew
			Oid=1.3.6.1.4.1.31968.3.1.4.1.2.157
			"
	::= { unitConfigItems 157 }

acuMaxSkew OBJECT-TYPE
	SYNTAX		Unsigned32
	UNITS		"0.001 Degree"
	MAX-ACCESS	read-write
	STATUS		current
	DESCRIPTION "Max Skew
			Oid=1.3.6.1.4.1.31968.3.1.4.1.2.158
			"
	::= { unitConfigItems 158 }

acuTxCableLoss OBJECT-TYPE
	SYNTAX		Unsigned32
	UNITS		"0.01 dB"
	MAX-ACCESS	read-write
	STATUS		current
	DESCRIPTION "Tx Cable Loss
			Oid=1.3.6.1.4.1.31968.3.1.4.1.2.159
			"
	::= { unitConfigItems 159 }

acuRegulationType OBJECT-TYPE
	SYNTAX		INTEGER {
		fccgeo(0),
		fccngso(1),
		etsigeo(2),
		etsingso(3)
	}
	MAX-ACCESS	read-write
	STATUS		current
	DESCRIPTION "Regulation Type, where:
			    0) 'FCCGEO'
			    1) 'FCCNGSO'
			    2) 'ETSIGEO'
			    3) 'ETSINGSO'
			Oid=1.3.6.1.4.1.31968.3.1.4.1.2.160
			"
	::= { unitConfigItems 160 }

acuRegReportingInterval OBJECT-TYPE
	SYNTAX		Unsigned32
	UNITS		"s"
	MAX-ACCESS	read-write
	STATUS		current
	DESCRIPTION "Reporting Interval
			Oid=1.3.6.1.4.1.31968.3.1.4.1.2.161
			"
	::= { unitConfigItems 161 }

acuSatLongitude OBJECT-TYPE
	SYNTAX		Integer32
	UNITS		"0.001 Degree"
	MAX-ACCESS	read-write
	STATUS		current
	DESCRIPTION "Satellite Longitude
			Oid=1.3.6.1.4.1.31968.3.1.4.1.2.162
			"
	::= { unitConfigItems 162 }

acuSatLatitudeVariance OBJECT-TYPE
	SYNTAX		Integer32
	UNITS		"0.001 Degree"
	MAX-ACCESS	read-write
	STATUS		current
	DESCRIPTION "Satellite Latitude Variance
			Oid=1.3.6.1.4.1.31968.3.1.4.1.2.163
			"
	::= { unitConfigItems 163 }

acuPolarizationSkew OBJECT-TYPE
	SYNTAX		Integer32
	UNITS		"0.001 Degree"
	MAX-ACCESS	read-write
	STATUS		current
	DESCRIPTION "Satellite Polarization Skew
			Oid=1.3.6.1.4.1.31968.3.1.4.1.2.164
			"
	::= { unitConfigItems 164 }

acuSendCommand OBJECT-TYPE
	SYNTAX		INTEGER {
		idle(0),
		txMuteOn(1),
		txMuteOff(2),
		findSatelliite(3),
		checkSatellite(4),
		stopAntenna(5),
		parkAntenna(6),
		stowAntenna(7),
		reserved(8)
	}
	MAX-ACCESS	read-write
	STATUS		current
	DESCRIPTION "Send Command to ACU, where:
			    0) 'Idle'
			    1) 'Tx Mute On'
			    2) 'Tx Mute Off'
			    3) 'Find Satelliite'
			    4) 'Check Satellite'
			    5) 'Stop Antenna'
			    6) 'Park Antenna'
			    7) 'Stow Antenna'
			    8) 'Reserved'
			Oid=1.3.6.1.4.1.31968.3.1.4.1.2.165
			"
	::= { unitConfigItems 165 }

acuHuntFreq OBJECT-TYPE
	SYNTAX		Unsigned32
	UNITS		"1 Hz"
	MAX-ACCESS	read-write
	STATUS		current
	DESCRIPTION "Hunt Frequency
			Oid=1.3.6.1.4.1.31968.3.1.4.1.2.168
			"
	::= { unitConfigItems 168 }

acuHuntBandwidth OBJECT-TYPE
	SYNTAX		Unsigned32
	UNITS		"1 Hz"
	MAX-ACCESS	read-write
	STATUS		current
	DESCRIPTION "Hunt Bandwidth
			Oid=1.3.6.1.4.1.31968.3.1.4.1.2.169
			"
	::= { unitConfigItems 169 }

acuRxChannel OBJECT-TYPE
	SYNTAX		Unsigned32
	UNITS		"1"
	MAX-ACCESS	read-write
	STATUS		current
	DESCRIPTION "Rx Channel Source
			Oid=1.3.6.1.4.1.31968.3.1.4.1.2.170
			"
	::= { unitConfigItems 170 }

acuAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "ACU Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.2.171
			"
	::= { unitConfigItems 171 }

acuEvent OBJECT-TYPE
	SYNTAX		INTEGER {
		doNotLog(0),
		log(1),
		logAndSendAlert(2),
		logAndSendAlertNowNoDebounce(3)
	}
	MAX-ACCESS	read-write
	STATUS		current
	DESCRIPTION "ACU Event, where:
			    0) 'Do Not Log'
			    1) 'Log'
			    2) 'Log & Send Alert'
			    3) 'Log & Send Alert Now (No Debounce)'
			Oid=1.3.6.1.4.1.31968.3.1.4.1.2.172
			"
	::= { unitConfigItems 172 }

redundancyRole OBJECT-TYPE
	SYNTAX		INTEGER {
		standAlone(0),
		internal1For1(1)
	}
	MAX-ACCESS	read-write
	STATUS		current
	DESCRIPTION "Unit Role, where:
			    0) 'Stand Alone'
			    1) 'Internal 1 for 1'
			Oid=1.3.6.1.4.1.31968.3.1.4.1.2.173
			"
	::= { unitConfigItems 173 }

redundancyPreference OBJECT-TYPE
	SYNTAX		INTEGER {
		primary(0),
		backup(1)
	}
	MAX-ACCESS	read-write
	STATUS		current
	DESCRIPTION "Preference, where:
			    0) 'Primary'
			    1) 'Backup'
			Oid=1.3.6.1.4.1.31968.3.1.4.1.2.174
			"
	::= { unitConfigItems 174 }

redundancyComs OBJECT-TYPE
	SYNTAX		INTEGER {
		ipControl(0)
	}
	MAX-ACCESS	read-write
	STATUS		current
	DESCRIPTION "Communication Port, where:
			    0) 'IP Control'
			Oid=1.3.6.1.4.1.31968.3.1.4.1.2.175
			"
	::= { unitConfigItems 175 }

redundancyPartnerIp OBJECT-TYPE
	SYNTAX		IpAddress
	MAX-ACCESS	read-write
	STATUS		current
	DESCRIPTION "Partner IP Address
			Oid=1.3.6.1.4.1.31968.3.1.4.1.2.176
			"
	::= { unitConfigItems 176 }

redundancySwitchDelay OBJECT-TYPE
	SYNTAX		Unsigned32
	UNITS		"0.1 s"
	MAX-ACCESS	read-write
	STATUS		current
	DESCRIPTION "Switch Delay
			Oid=1.3.6.1.4.1.31968.3.1.4.1.2.177
			"
	::= { unitConfigItems 177 }

redundancyLossAction OBJECT-TYPE
	SYNTAX		INTEGER {
		goOnline(0),
		goOffline(1),
		keepLastState(2)
	}
	MAX-ACCESS	read-write
	STATUS		current
	DESCRIPTION "Comms Loss Action, where:
			    0) 'Go Online'
			    1) 'Go Offline'
			    2) 'Keep Last State'
			Oid=1.3.6.1.4.1.31968.3.1.4.1.2.178
			"
	::= { unitConfigItems 178 }

redundancyConfigTransfer OBJECT-TYPE
	SYNTAX		INTEGER {
		idle(0),
		transferAll(1)
	}
	MAX-ACCESS	read-write
	STATUS		current
	DESCRIPTION "Configuration Transfer, where:
			    0) 'Idle'
			    1) 'Transfer All'
			Oid=1.3.6.1.4.1.31968.3.1.4.1.2.179
			"
	::= { unitConfigItems 179 }

redundancyPort OBJECT-TYPE
	SYNTAX		Unsigned32
	UNITS		"1"
	MAX-ACCESS	read-write
	STATUS		current
	DESCRIPTION "Redundancy Port
			Oid=1.3.6.1.4.1.31968.3.1.4.1.2.180
			"
	::= { unitConfigItems 180 }

redundancyAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Redundancy Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.2.181
			"
	::= { unitConfigItems 181 }

redundancyRevDelay OBJECT-TYPE
	SYNTAX		Unsigned32
	MAX-ACCESS	read-write
	STATUS		current
	DESCRIPTION "Revertive Switch Delay
			Oid=1.3.6.1.4.1.31968.3.1.4.1.2.182
			"
	::= { unitConfigItems 182 }

fipsSelfTest OBJECT-TYPE
	SYNTAX		INTEGER {
		idle(0),
		fullFipsSelfTest(1),
		reloadFipsWithFullSelfTest(2)
	}
	MAX-ACCESS	read-write
	STATUS		current
	DESCRIPTION "FIPS Self Test, where:
			    0) 'Idle'
			    1) 'Full FIPS Self Test'
			    2) 'Reload FIPS With Full Self Test'
			Oid=1.3.6.1.4.1.31968.3.1.4.1.2.184
			"
	::= { unitConfigItems 184 }

fipsAuthenication OBJECT-TYPE
	SYNTAX		INTEGER {
		coIdentifierNotSet(0),
		coIdentifierSet(1),
		zeroizeCoTxAndRx(2)
	}
	MAX-ACCESS	read-write
	STATUS		current
	DESCRIPTION "Authentication, where:
			    0) 'CO Identifier Not Set'
			    1) 'CO Identifier Set'
			    2) 'Zeroize CO, Tx & Rx'
			Oid=1.3.6.1.4.1.31968.3.1.4.1.2.185
			"
	::= { unitConfigItems 185 }

fipsAuthenicationIdentifier OBJECT-TYPE
	SYNTAX		DisplayString(SIZE(0..70))
	MAX-ACCESS	read-write
	STATUS		current
	DESCRIPTION "CO Authentication Identifier
			Oid=1.3.6.1.4.1.31968.3.1.4.1.2.186
			"
	::= { unitConfigItems 186 }

sshServerMode OBJECT-TYPE
	SYNTAX		INTEGER {
		off(0),
		readOnly(1),
		fullAccess(2)
	}
	MAX-ACCESS	read-write
	STATUS		current
	DESCRIPTION "Server Mode, where:
			    0) 'Off'
			    1) 'Read Only'
			    2) 'Full Access'
			Oid=1.3.6.1.4.1.31968.3.1.4.1.2.187
			"
	::= { unitConfigItems 187 }

sshServerPort OBJECT-TYPE
	SYNTAX		Unsigned32
	UNITS		"1"
	MAX-ACCESS	read-write
	STATUS		current
	DESCRIPTION "Server Port Number
			Oid=1.3.6.1.4.1.31968.3.1.4.1.2.188
			"
	::= { unitConfigItems 188 }

sshReadName OBJECT-TYPE
	SYNTAX		DisplayString(SIZE(5..28))
	MAX-ACCESS	read-write
	STATUS		current
	DESCRIPTION "Read Access Name
			Oid=1.3.6.1.4.1.31968.3.1.4.1.2.189
			"
	::= { unitConfigItems 189 }

sshReadPassword OBJECT-TYPE
	SYNTAX		DisplayString(SIZE(5..28))
	MAX-ACCESS	read-write
	STATUS		current
	DESCRIPTION "Read Access Password
			Oid=1.3.6.1.4.1.31968.3.1.4.1.2.190
			"
	::= { unitConfigItems 190 }

sshFullName OBJECT-TYPE
	SYNTAX		DisplayString(SIZE(5..28))
	MAX-ACCESS	read-write
	STATUS		current
	DESCRIPTION "Full Access Name
			Oid=1.3.6.1.4.1.31968.3.1.4.1.2.191
			"
	::= { unitConfigItems 191 }

sshFullPassword OBJECT-TYPE
	SYNTAX		DisplayString(SIZE(5..28))
	MAX-ACCESS	read-write
	STATUS		current
	DESCRIPTION "Full Access Password
			Oid=1.3.6.1.4.1.31968.3.1.4.1.2.192
			"
	::= { unitConfigItems 192 }

sshActivity OBJECT-TYPE
	SYNTAX		INTEGER {
		none(0),
		flashOnline(1)
	}
	MAX-ACCESS	read-write
	STATUS		current
	DESCRIPTION "Activity, where:
			    0) 'None'
			    1) 'Flash Online'
			Oid=1.3.6.1.4.1.31968.3.1.4.1.2.193
			"
	::= { unitConfigItems 193 }

mgmtPortLink OBJECT-TYPE
	SYNTAX		INTEGER {
		auto(0),
		n10Mb(1),
		n100Mb(2),
		n1Gb(3)
	}
	MAX-ACCESS	read-write
	STATUS		current
	DESCRIPTION "Mgmt Port Link, where:
			    0) 'Auto'
			    1) '10 Mb'
			    2) '100 Mb'
			    3) '1 Gb'
			Oid=1.3.6.1.4.1.31968.3.1.4.1.2.194
			"
	::= { unitConfigItems 194 }

dataPortExternalLoop OBJECT-TYPE
	SYNTAX		INTEGER {
		off(0),
		on(1)
	}
	MAX-ACCESS	read-write
	STATUS		current
	DESCRIPTION "Ingress/Egress Loopback, where:
			    0) 'Off'
			    1) 'On'
			Oid=1.3.6.1.4.1.31968.3.1.4.1.2.195
			"
	::= { unitConfigItems 195 }

dataPortInternalLoop OBJECT-TYPE
	SYNTAX		INTEGER {
		off(0),
		on(1)
	}
	MAX-ACCESS	read-write
	STATUS		current
	DESCRIPTION "Rx/Tx Internal Data Loopback, where:
			    0) 'Off'
			    1) 'On'
			Oid=1.3.6.1.4.1.31968.3.1.4.1.2.196
			"
	::= { unitConfigItems 196 }

ntpServer1 OBJECT-TYPE
	SYNTAX		IpAddress
	MAX-ACCESS	read-write
	STATUS		current
	DESCRIPTION "NTP Server 1,
			    0.0.0.0=Off
			Oid=1.3.6.1.4.1.31968.3.1.4.1.2.197
			"
	::= { unitConfigItems 197 }

ntpServer2 OBJECT-TYPE
	SYNTAX		IpAddress
	MAX-ACCESS	read-write
	STATUS		current
	DESCRIPTION "NTP Server 2,
			    0.0.0.0=Off
			Oid=1.3.6.1.4.1.31968.3.1.4.1.2.198
			"
	::= { unitConfigItems 198 }

rxSumStatus OBJECT-TYPE
	SYNTAX		INTEGER {
		allChannelsLockedOk(0),
		allChannelsLockedOffline(1),
		channel16MinorAlarm(2),
		channel15MinorAlarm(3),
		channel14MinorAlarm(4),
		channel13MinorAlarm(5),
		channel12MinorAlarm(6),
		channel11MinorAlarm(7),
		channel10MinorAlarm(8),
		channel9MinorAlarm(9),
		channel8MinorAlarm(10),
		channel7MinorAlarm(11),
		channel6MinorAlarm(12),
		channel5MinorAlarm(13),
		channel4MinorAlarm(14),
		channel3MinorAlarm(15),
		channel2MinorAlarm(16),
		channel1MinorAlarm(17),
		channel16MajorAlarm(18),
		channel15MajorAlarm(19),
		channel14MajorAlarm(20),
		channel13MajorAlarm(21),
		channel12MajorAlarm(22),
		channel11MajorAlarm(23),
		channel10MajorAlarm(24),
		channel9MajorAlarm(25),
		channel8MajorAlarm(26),
		channel7MajorAlarm(27),
		channel6MajorAlarm(28),
		channel5MajorAlarm(29),
		channel4MajorAlarm(30),
		channel3MajorAlarm(31),
		channel2MajorAlarm(32),
		channel1MajorAlarm(33),
		channel16Unlocked(34),
		channel15Unlocked(35),
		channel14Unlocked(36),
		channel13Unlocked(37),
		channel12Unlocked(38),
		channel11Unlocked(39),
		channel10Unlocked(40),
		channel9Unlocked(41),
		channel8Unlocked(42),
		channel7Unlocked(43),
		channel6Unlocked(44),
		channel5Unlocked(45),
		channel4Unlocked(46),
		channel3Unlocked(47),
		channel2Unlocked(48),
		channel1Unlocked(49),
		allChannelsUnlocked(50),
		echoUnlocked(51),
		allChannelsOff(52),
		lnbAlarm(53),
		ocxoAlarm(54),
		calibrationFailed(55),
		hardwareAlarm(56),
		systemAlarm(57),
		overTemperature(58),
		overTemperatureShutdown(59),
		loadFailed(60)
	}
	MAX-ACCESS	read-only
	STATUS		current
	DESCRIPTION "Rx Summary Status, where:
			    0) 'All Channels Locked, Ok'
			    1) 'All Channels Locked Offline'
			    2) 'CHANNEL 16 MINOR ALARM'
			    3) 'CHANNEL 15 MINOR ALARM'
			    4) 'CHANNEL 14 MINOR ALARM'
			    5) 'CHANNEL 13 MINOR ALARM'
			    6) 'CHANNEL 12 MINOR ALARM'
			    7) 'CHANNEL 11 MINOR ALARM'
			    8) 'CHANNEL 10 MINOR ALARM'
			    9) 'CHANNEL 9 MINOR ALARM'
			    10) 'CHANNEL 8 MINOR ALARM'
			    11) 'CHANNEL 7 MINOR ALARM'
			    12) 'CHANNEL 6 MINOR ALARM'
			    13) 'CHANNEL 5 MINOR ALARM'
			    14) 'CHANNEL 4 MINOR ALARM'
			    15) 'CHANNEL 3 MINOR ALARM'
			    16) 'CHANNEL 2 MINOR ALARM'
			    17) 'CHANNEL 1 MINOR ALARM'
			    18) 'CHANNEL 16 MAJOR ALARM'
			    19) 'CHANNEL 15 MAJOR ALARM'
			    20) 'CHANNEL 14 MAJOR ALARM'
			    21) 'CHANNEL 13 MAJOR ALARM'
			    22) 'CHANNEL 12 MAJOR ALARM'
			    23) 'CHANNEL 11 MAJOR ALARM'
			    24) 'CHANNEL 10 MAJOR ALARM'
			    25) 'CHANNEL 9 MAJOR ALARM'
			    26) 'CHANNEL 8 MAJOR ALARM'
			    27) 'CHANNEL 7 MAJOR ALARM'
			    28) 'CHANNEL 6 MAJOR ALARM'
			    29) 'CHANNEL 5 MAJOR ALARM'
			    30) 'CHANNEL 4 MAJOR ALARM'
			    31) 'CHANNEL 3 MAJOR ALARM'
			    32) 'CHANNEL 2 MAJOR ALARM'
			    33) 'CHANNEL 1 MAJOR ALARM'
			    34) 'CHANNEL 16 UNLOCKED'
			    35) 'CHANNEL 15 UNLOCKED'
			    36) 'CHANNEL 14 UNLOCKED'
			    37) 'CHANNEL 13 UNLOCKED'
			    38) 'CHANNEL 12 UNLOCKED'
			    39) 'CHANNEL 11 UNLOCKED'
			    40) 'CHANNEL 10 UNLOCKED'
			    41) 'CHANNEL 9 UNLOCKED'
			    42) 'CHANNEL 8 UNLOCKED'
			    43) 'CHANNEL 7 UNLOCKED'
			    44) 'CHANNEL 6 UNLOCKED'
			    45) 'CHANNEL 5 UNLOCKED'
			    46) 'CHANNEL 4 UNLOCKED'
			    47) 'CHANNEL 3 UNLOCKED'
			    48) 'CHANNEL 2 UNLOCKED'
			    49) 'CHANNEL 1 UNLOCKED'
			    50) 'ALL CHANNELS UNLOCKED'
			    51) 'ECHO UNLOCKED'
			    52) 'All Channels Off'
			    53) 'LNB ALARM'
			    54) 'OCXO ALARM'
			    55) 'CALIBRATION FAILED'
			    56) 'HARDWARE ALARM'
			    57) 'SYSTEM ALARM'
			    58) 'OVER TEMPERATURE'
			    59) 'OVER TEMPERATURE SHUTDOWN'
			    60) 'LOAD FAILED'
			Oid=1.3.6.1.4.1.31968.3.1.4.1.3.1
			"
	::= { rxStatusItems 1 }

rxBinary0Status OBJECT-TYPE
	SYNTAX		BITS {
		lock1(0),
		lock2(1),
		lock3(2),
		lock4(3),
		lock5(4),
		lock6(5),
		lock7(6),
		lock8(7),
		lock9(8),
		lock10(9),
		lock11(10),
		lock12(11),
		lock13(12),
		lock14(13),
		lock15(14),
		lock16(15),
		lowMargin1(16),
		lowMargin2(17),
		lowMargin3(18),
		lowMargin4(19),
		lowMargin5(20),
		lowMargin6(21),
		lowMargin7(22),
		lowMargin8(23),
		lowMargin9(24),
		lowMargin10(25),
		lowMargin11(26),
		lowMargin12(27),
		lowMargin13(28),
		lowMargin14(29),
		lowMargin15(30),
		lowMargin16(31),
		lowLevel1(32),
		lowLevel2(33),
		lowLevel3(34),
		lowLevel4(35),
		lowLevel5(36),
		lowLevel6(37),
		lowLevel7(38),
		lowLevel8(39),
		lowLevel9(40),
		lowLevel10(41),
		lowLevel11(42),
		lowLevel12(43),
		lowLevel13(44),
		lowLevel14(45),
		lowLevel15(46),
		lowLevel16(47),
		spctInv1(48),
		spctInv2(49),
		spctInv3(50),
		spctInv4(51),
		spctInv5(52),
		spctInv6(53),
		spctInv7(54),
		spctInv8(55),
		spctInv9(56),
		spctInv10(57),
		spctInv11(58),
		spctInv12(59),
		spctInv13(60),
		spctInv14(61),
		spctInv15(62),
		spctInv16(63),
		dataUp1(64),
		dataUp2(65),
		dataUp3(66),
		dataUp4(67),
		dataUp5(68),
		dataUp6(69),
		dataUp7(70),
		dataUp8(71),
		dataUp9(72),
		dataUp10(73),
		dataUp11(74),
		dataUp12(75),
		dataUp13(76),
		dataUp14(77),
		dataUp15(78),
		dataUp16(79),
		pending1(80),
		pending2(81),
		pending3(82),
		pending4(83),
		pending5(84),
		pending6(85),
		pending7(86),
		pending8(87),
		pending9(88),
		pending10(89),
		pending11(90),
		pending12(91),
		pending13(92),
		pending14(93),
		pending15(94),
		pending16(95),
		almLowAcm1(96),
		almLowAcm2(97),
		almLowAcm3(98),
		almLowAcm4(99),
		almLowAcm5(100),
		almLowAcm6(101),
		almLowAcm7(102),
		almLowAcm8(103),
		almLowAcm9(104),
		almLowAcm10(105),
		almLowAcm11(106),
		almLowAcm12(107),
		almLowAcm13(108),
		almLowAcm14(109),
		almLowAcm15(110),
		almLowAcm16(111),
		almData1(112),
		almData2(113),
		almData3(114),
		almData4(115),
		almData5(116),
		almData6(117),
		almData7(118),
		almData8(119),
		almData9(120),
		almData10(121),
		almData11(122),
		almData12(123),
		almData13(124),
		almData14(125),
		almData15(126),
		almData16(127),
		almTransec1(128),
		almTransec2(129),
		almTransec3(130),
		almTransec4(131),
		almTransec5(132),
		almTransec6(133),
		almTransec7(134),
		almTransec8(135),
		almTransec9(136),
		almTransec10(137),
		almTransec11(138),
		almTransec12(139),
		almTransec13(140),
		almTransec14(141),
		almTransec15(142),
		almTransec16(143),
		almMismatch1(144),
		almMismatch2(145),
		almMismatch3(146),
		almMismatch4(147),
		almMismatch5(148),
		almMismatch6(149),
		almMismatch7(150),
		almMismatch8(151),
		almMismatch9(152),
		almMismatch10(153),
		almMismatch11(154),
		almMismatch12(155),
		almMismatch13(156),
		almMismatch14(157),
		almMismatch15(158),
		almMismatch16(159)
	}
	MAX-ACCESS	read-only
	STATUS		current
	DESCRIPTION "Rx Binary 0 Status, where:
			    0) 'Lock 1'
			    1) 'Lock 2'
			    2) 'Lock 3'
			    3) 'Lock 4'
			    4) 'Lock 5'
			    5) 'Lock 6'
			    6) 'Lock 7'
			    7) 'Lock 8'
			    8) 'Lock 9'
			    9) 'Lock 10'
			    10) 'Lock 11'
			    11) 'Lock 12'
			    12) 'Lock 13'
			    13) 'Lock 14'
			    14) 'Lock 15'
			    15) 'Lock 16'
			    16) 'Low Margin 1'
			    17) 'Low Margin 2'
			    18) 'Low Margin 3'
			    19) 'Low Margin 4'
			    20) 'Low Margin 5'
			    21) 'Low Margin 6'
			    22) 'Low Margin 7'
			    23) 'Low Margin 8'
			    24) 'Low Margin 9'
			    25) 'Low Margin 10'
			    26) 'Low Margin 11'
			    27) 'Low Margin 12'
			    28) 'Low Margin 13'
			    29) 'Low Margin 14'
			    30) 'Low Margin 15'
			    31) 'Low Margin 16'
			    32) 'Low Level 1'
			    33) 'Low Level 2'
			    34) 'Low Level 3'
			    35) 'Low Level 4'
			    36) 'Low Level 5'
			    37) 'Low Level 6'
			    38) 'Low Level 7'
			    39) 'Low Level 8'
			    40) 'Low Level 9'
			    41) 'Low Level 10'
			    42) 'Low Level 11'
			    43) 'Low Level 12'
			    44) 'Low Level 13'
			    45) 'Low Level 14'
			    46) 'Low Level 15'
			    47) 'Low Level 16'
			    48) 'Spct Inv 1'
			    49) 'Spct Inv 2'
			    50) 'Spct Inv 3'
			    51) 'Spct Inv 4'
			    52) 'Spct Inv 5'
			    53) 'Spct Inv 6'
			    54) 'Spct Inv 7'
			    55) 'Spct Inv 8'
			    56) 'Spct Inv 9'
			    57) 'Spct Inv 10'
			    58) 'Spct Inv 11'
			    59) 'Spct Inv 12'
			    60) 'Spct Inv 13'
			    61) 'Spct Inv 14'
			    62) 'Spct Inv 15'
			    63) 'Spct Inv 16'
			    64) 'Data Up 1'
			    65) 'Data Up 2'
			    66) 'Data Up 3'
			    67) 'Data Up 4'
			    68) 'Data Up 5'
			    69) 'Data Up 6'
			    70) 'Data Up 7'
			    71) 'Data Up 8'
			    72) 'Data Up 9'
			    73) 'Data Up 10'
			    74) 'Data Up 11'
			    75) 'Data Up 12'
			    76) 'Data Up 13'
			    77) 'Data Up 14'
			    78) 'Data Up 15'
			    79) 'Data Up 16'
			    80) 'Pending 1'
			    81) 'Pending 2'
			    82) 'Pending 3'
			    83) 'Pending 4'
			    84) 'Pending 5'
			    85) 'Pending 6'
			    86) 'Pending 7'
			    87) 'Pending 8'
			    88) 'Pending 9'
			    89) 'Pending 10'
			    90) 'Pending 11'
			    91) 'Pending 12'
			    92) 'Pending 13'
			    93) 'Pending 14'
			    94) 'Pending 15'
			    95) 'Pending 16'
			    96) 'Alm Low ACM 1'
			    97) 'Alm Low ACM 2'
			    98) 'Alm Low ACM 3'
			    99) 'Alm Low ACM 4'
			    100) 'Alm Low ACM 5'
			    101) 'Alm Low ACM 6'
			    102) 'Alm Low ACM 7'
			    103) 'Alm Low ACM 8'
			    104) 'Alm Low ACM 9'
			    105) 'Alm Low ACM 10'
			    106) 'Alm Low ACM 11'
			    107) 'Alm Low ACM 12'
			    108) 'Alm Low ACM 13'
			    109) 'Alm Low ACM 14'
			    110) 'Alm Low ACM 15'
			    111) 'Alm Low ACM 16'
			    112) 'Alm Data 1'
			    113) 'Alm Data 2'
			    114) 'Alm Data 3'
			    115) 'Alm Data 4'
			    116) 'Alm Data 5'
			    117) 'Alm Data 6'
			    118) 'Alm Data 7'
			    119) 'Alm Data 8'
			    120) 'Alm Data 9'
			    121) 'Alm Data 10'
			    122) 'Alm Data 11'
			    123) 'Alm Data 12'
			    124) 'Alm Data 13'
			    125) 'Alm Data 14'
			    126) 'Alm Data 15'
			    127) 'Alm Data 16'
			    128) 'Alm TRANSEC 1'
			    129) 'Alm TRANSEC 2'
			    130) 'Alm TRANSEC 3'
			    131) 'Alm TRANSEC 4'
			    132) 'Alm TRANSEC 5'
			    133) 'Alm TRANSEC 6'
			    134) 'Alm TRANSEC 7'
			    135) 'Alm TRANSEC 8'
			    136) 'Alm TRANSEC 9'
			    137) 'Alm TRANSEC 10'
			    138) 'Alm TRANSEC 11'
			    139) 'Alm TRANSEC 12'
			    140) 'Alm TRANSEC 13'
			    141) 'Alm TRANSEC 14'
			    142) 'Alm TRANSEC 15'
			    143) 'Alm TRANSEC 16'
			    144) 'Alm Mismatch 1'
			    145) 'Alm Mismatch 2'
			    146) 'Alm Mismatch 3'
			    147) 'Alm Mismatch 4'
			    148) 'Alm Mismatch 5'
			    149) 'Alm Mismatch 6'
			    150) 'Alm Mismatch 7'
			    151) 'Alm Mismatch 8'
			    152) 'Alm Mismatch 9'
			    153) 'Alm Mismatch 10'
			    154) 'Alm Mismatch 11'
			    155) 'Alm Mismatch 12'
			    156) 'Alm Mismatch 13'
			    157) 'Alm Mismatch 14'
			    158) 'Alm Mismatch 15'
			    159) 'Alm Mismatch 16'
			Oid=1.3.6.1.4.1.31968.3.1.4.1.3.2
			"
	::= { rxStatusItems 2 }

rxBinary1Status OBJECT-TYPE
	SYNTAX		BITS {
		almEchoLock(0),
		almEchoLevel(1),
		almEchoOffset(2),
		almAgcMin(3),
		almAgcMax(4),
		almLnbPower(5),
		almKey(6),
		almLoad1(7),
		almTemp1(8),
		almVint1(9),
		almVaux1(10),
		almClock1(11),
		almMemory1(12),
		almLoad2(13),
		almVint2(14),
		almVaux2(15),
		almClock2(16),
		almMemory2(17),
		alm100Mhz(18),
		almLo(19),
		almRfTemp(20),
		almTempShutdown(21),
		trialActive(22),
		almLinkRate(23),
		almAcmTxHub(24)
	}
	MAX-ACCESS	read-only
	STATUS		current
	DESCRIPTION "Rx Binary 1 Status, where:
			    0) 'Alm Echo Lock'
			    1) 'Alm Echo Level'
			    2) 'Alm Echo Offset'
			    3) 'Alm AGC Min'
			    4) 'Alm AGC Max'
			    5) 'Alm LNB Power'
			    6) 'Alm Key'
			    7) 'Alm Load1'
			    8) 'Alm Temp1'
			    9) 'Alm VInt1'
			    10) 'Alm VAux1'
			    11) 'Alm Clock1'
			    12) 'Alm Memory1'
			    13) 'Alm Load2'
			    14) 'Alm VInt2'
			    15) 'Alm VAux2'
			    16) 'Alm Clock2'
			    17) 'Alm Memory2'
			    18) 'Alm 100 MHz'
			    19) 'Alm LO'
			    20) 'Alm RF Temp'
			    21) 'Alm Temp Shutdown'
			    22) 'Trial Active'
			    23) 'Alm Link Rate'
			    24) 'Alm ACM Tx Hub'
			Oid=1.3.6.1.4.1.31968.3.1.4.1.3.3
			"
	::= { rxStatusItems 3 }

rxEchoLevel OBJECT-TYPE
	SYNTAX		Integer32
	UNITS		"0.01 dBm"
	MAX-ACCESS	read-only
	STATUS		current
	DESCRIPTION "Rx Sat Echo Level
			Oid=1.3.6.1.4.1.31968.3.1.4.1.3.4
			"
	::= { rxStatusItems 4 }

rxEchoOffset OBJECT-TYPE
	SYNTAX		Integer32
	UNITS		"1 Hz"
	MAX-ACCESS	read-only
	STATUS		current
	DESCRIPTION "Rx Sat Echo Offset
			Oid=1.3.6.1.4.1.31968.3.1.4.1.3.5
			"
	::= { rxStatusItems 5 }

rxOffsetImbalance OBJECT-TYPE
	SYNTAX		Integer32
	UNITS		"0.01%"
	MAX-ACCESS	read-only
	STATUS		current
	DESCRIPTION "Rx Offset Imbalance
			Oid=1.3.6.1.4.1.31968.3.1.4.1.3.6
			"
	::= { rxStatusItems 6 }

rxEchoDelay OBJECT-TYPE
	SYNTAX		Unsigned32
	UNITS		"0.1 ms"
	MAX-ACCESS	read-only
	STATUS		current
	DESCRIPTION "Rx Sat Echo Delay
			Oid=1.3.6.1.4.1.31968.3.1.4.1.3.7
			"
	::= { rxStatusItems 7 }

rxFeatureBitRateLimit OBJECT-TYPE
	SYNTAX		Unsigned32
	UNITS		"1 bps"
	MAX-ACCESS	read-only
	STATUS		current
	DESCRIPTION "Rx Bit Rate Limit
			Oid=1.3.6.1.4.1.31968.3.1.4.1.3.12
			"
	::= { rxStatusItems 12 }

rxFeatureSymbolRateLimit OBJECT-TYPE
	SYNTAX		Unsigned32
	UNITS		"1 sps"
	MAX-ACCESS	read-only
	STATUS		current
	DESCRIPTION "Rx Symbol/Chip Rate Limit
			Oid=1.3.6.1.4.1.31968.3.1.4.1.3.13
			"
	::= { rxStatusItems 13 }

rxFeatureModulationLimit OBJECT-TYPE
	SYNTAX		INTEGER {
		n4Ary(0),
		n8Ary(1),
		n16Ary(2),
		n32Ary(3),
		n64Ary(4),
		n128Ary(5),
		n256Ary(6)
	}
	MAX-ACCESS	read-only
	STATUS		current
	DESCRIPTION "Rx Modulation Limit, where:
			    0) '4-ary'
			    1) '8-ary'
			    2) '16-ary'
			    3) '32-ary'
			    4) '64-ary'
			    5) '128-ary'
			    6) '256-ary'
			Oid=1.3.6.1.4.1.31968.3.1.4.1.3.14
			"
	::= { rxStatusItems 14 }

rxFeatureChannelLimit OBJECT-TYPE
	SYNTAX		Unsigned32
	UNITS		"1"
	MAX-ACCESS	read-only
	STATUS		current
	DESCRIPTION "Rx Channel Limit
			Oid=1.3.6.1.4.1.31968.3.1.4.1.3.15
			"
	::= { rxStatusItems 15 }

rxFeatureWaveforms OBJECT-TYPE
	SYNTAX		DisplayString
	MAX-ACCESS	read-only
	STATUS		current
	DESCRIPTION "Rx Waveforms
			Oid=1.3.6.1.4.1.31968.3.1.4.1.3.16
			"
	::= { rxStatusItems 16 }

rxLnbVoltage OBJECT-TYPE
	SYNTAX		Unsigned32
	UNITS		"0.01 V"
	MAX-ACCESS	read-only
	STATUS		current
	DESCRIPTION "Rx LNB Voltage
			Oid=1.3.6.1.4.1.31968.3.1.4.1.3.17
			"
	::= { rxStatusItems 17 }

rxLnbCurrent OBJECT-TYPE
	SYNTAX		Unsigned32
	UNITS		"1 ma"
	MAX-ACCESS	read-only
	STATUS		current
	DESCRIPTION "Rx LNB Current
			Oid=1.3.6.1.4.1.31968.3.1.4.1.3.18
			"
	::= { rxStatusItems 18 }

rxTotalSymbolRate OBJECT-TYPE
	SYNTAX		Unsigned32
	UNITS		"1 sps"
	MAX-ACCESS	read-only
	STATUS		current
	DESCRIPTION "Rx Total Symbol Rate
			Oid=1.3.6.1.4.1.31968.3.1.4.1.3.19
			"
	::= { rxStatusItems 19 }

rxEchoDrops OBJECT-TYPE
	SYNTAX		DisplayString(SIZE(1..24))
	UNITS		"1"
	MAX-ACCESS	read-only
	STATUS		current
	DESCRIPTION "Rx Echo Drops,
			    Text Number, Decimal
			Oid=1.3.6.1.4.1.31968.3.1.4.1.3.20
			"
	::= { rxStatusItems 20 }

rxTotalBitRate OBJECT-TYPE
	SYNTAX		Unsigned32
	UNITS		"1 bps"
	MAX-ACCESS	read-only
	STATUS		current
	DESCRIPTION "Rx Total Bit Rate
			Oid=1.3.6.1.4.1.31968.3.1.4.1.3.22
			"
	::= { rxStatusItems 22 }

rxAnalyzerData OBJECT-TYPE
	SYNTAX		DisplayString(SIZE(0..4000))
	MAX-ACCESS	read-only
	STATUS		current
	DESCRIPTION "Rx Spectrum Analyzer Data
			Oid=1.3.6.1.4.1.31968.3.1.4.1.3.24
			"
	::= { rxStatusItems 24 }

rxAnalyzerTick OBJECT-TYPE
	SYNTAX		Unsigned32
	MAX-ACCESS	read-only
	STATUS		current
	DESCRIPTION "Rx Spectrum Analyzer Tick
			Oid=1.3.6.1.4.1.31968.3.1.4.1.3.25
			"
	::= { rxStatusItems 25 }

rxCalStatus OBJECT-TYPE
	SYNTAX		DisplayString
	MAX-ACCESS	read-only
	STATUS		current
	DESCRIPTION "Rx Cal Task Status
			Oid=1.3.6.1.4.1.31968.3.1.4.1.3.26
			"
	::= { rxStatusItems 26 }

rxLevelBalCal OBJECT-TYPE
	SYNTAX		DisplayString
	MAX-ACCESS	read-only
	STATUS		current
	DESCRIPTION "Rx Level Balance Cal Status
			Oid=1.3.6.1.4.1.31968.3.1.4.1.3.27
			"
	::= { rxStatusItems 27 }

rxPhaseBalCal OBJECT-TYPE
	SYNTAX		DisplayString
	MAX-ACCESS	read-only
	STATUS		current
	DESCRIPTION "Rx Phase Balance Cal Status
			Oid=1.3.6.1.4.1.31968.3.1.4.1.3.28
			"
	::= { rxStatusItems 28 }

rxEqBalCal OBJECT-TYPE
	SYNTAX		DisplayString
	MAX-ACCESS	read-only
	STATUS		current
	DESCRIPTION "Rx EQ Balance Cal Status
			Oid=1.3.6.1.4.1.31968.3.1.4.1.3.29
			"
	::= { rxStatusItems 29 }

rxLevelCal OBJECT-TYPE
	SYNTAX		DisplayString
	MAX-ACCESS	read-only
	STATUS		current
	DESCRIPTION "Rx Level Cal Status
			Oid=1.3.6.1.4.1.31968.3.1.4.1.3.30
			"
	::= { rxStatusItems 30 }

rxDmdMemTest OBJECT-TYPE
	SYNTAX		INTEGER {
		pass(0),
		fail(1)
	}
	MAX-ACCESS	read-only
	STATUS		current
	DESCRIPTION "Rx Demod Memory Test, where:
			    0) 'Pass'
			    1) 'FAIL'
			Oid=1.3.6.1.4.1.31968.3.1.4.1.3.31
			"
	::= { rxStatusItems 31 }

rxFecMemTest OBJECT-TYPE
	SYNTAX		INTEGER {
		pass(0),
		fail(1)
	}
	MAX-ACCESS	read-only
	STATUS		current
	DESCRIPTION "Rx FEC Memory Test, where:
			    0) 'Pass'
			    1) 'FAIL'
			Oid=1.3.6.1.4.1.31968.3.1.4.1.3.32
			"
	::= { rxStatusItems 32 }

rxFeatureTransec OBJECT-TYPE
	SYNTAX		INTEGER {
		none(0),
		aes128(1),
		aes128Aes192(2),
		aes128Aes192Aes256(3)
	}
	MAX-ACCESS	read-only
	STATUS		current
	DESCRIPTION "Rx TRANSEC, where:
			    0) 'None'
			    1) 'AES-128'
			    2) 'AES-128, AES-192'
			    3) 'AES-128, AES-192, AES-256'
			Oid=1.3.6.1.4.1.31968.3.1.4.1.3.33
			"
	::= { rxStatusItems 33 }

rxTrialWaveforms OBJECT-TYPE
	SYNTAX		DisplayString
	MAX-ACCESS	read-only
	STATUS		current
	DESCRIPTION "Rx Trial Waveforms
			Oid=1.3.6.1.4.1.31968.3.1.4.1.3.34
			"
	::= { rxStatusItems 34 }

rxTrialChannelLimit OBJECT-TYPE
	SYNTAX		Unsigned32
	UNITS		"1"
	MAX-ACCESS	read-only
	STATUS		current
	DESCRIPTION "Rx Trial Channel Limit
			Oid=1.3.6.1.4.1.31968.3.1.4.1.3.35
			"
	::= { rxStatusItems 35 }

rxTrialModulationLimit OBJECT-TYPE
	SYNTAX		INTEGER {
		n4Ary(0),
		n8Ary(1),
		n16Ary(2),
		n32Ary(3),
		n64Ary(4),
		n128Ary(5),
		n256Ary(6)
	}
	MAX-ACCESS	read-only
	STATUS		current
	DESCRIPTION "Rx Trial Modulation Limit, where:
			    0) '4-ary'
			    1) '8-ary'
			    2) '16-ary'
			    3) '32-ary'
			    4) '64-ary'
			    5) '128-ary'
			    6) '256-ary'
			Oid=1.3.6.1.4.1.31968.3.1.4.1.3.36
			"
	::= { rxStatusItems 36 }

rxTrialTransec OBJECT-TYPE
	SYNTAX		INTEGER {
		none(0),
		aes128(1),
		aes128Aes192(2),
		aes128Aes192Aes256(3)
	}
	MAX-ACCESS	read-only
	STATUS		current
	DESCRIPTION "Rx Trial TRANSEC, where:
			    0) 'None'
			    1) 'AES-128'
			    2) 'AES-128, AES-192'
			    3) 'AES-128, AES-192, AES-256'
			Oid=1.3.6.1.4.1.31968.3.1.4.1.3.37
			"
	::= { rxStatusItems 37 }

rxTrialBitRateLimit OBJECT-TYPE
	SYNTAX		Unsigned32
	UNITS		"1 bps"
	MAX-ACCESS	read-only
	STATUS		current
	DESCRIPTION "Rx Trial Bit Rate Limit
			Oid=1.3.6.1.4.1.31968.3.1.4.1.3.38
			"
	::= { rxStatusItems 38 }

rxTrialSymbolRateLimit OBJECT-TYPE
	SYNTAX		Unsigned32
	UNITS		"1 sps"
	MAX-ACCESS	read-only
	STATUS		current
	DESCRIPTION "Rx Trial Symbol Rate Limit
			Oid=1.3.6.1.4.1.31968.3.1.4.1.3.39
			"
	::= { rxStatusItems 39 }

rxDsssTotalChipRate OBJECT-TYPE
	SYNTAX		Unsigned32
	MAX-ACCESS	read-only
	STATUS		current
	DESCRIPTION "Rx DSSS Total Chip Rate
			Oid=1.3.6.1.4.1.31968.3.1.4.1.3.40
			"
	::= { rxStatusItems 40 }

rxHdrRotorOutage OBJECT-TYPE
	SYNTAX		Unsigned32
	UNITS		"0.1%"
	MAX-ACCESS	read-only
	STATUS		current
	DESCRIPTION "Rx Rotor Outage
			Oid=1.3.6.1.4.1.31968.3.1.4.1.3.41
			"
	::= { rxStatusItems 41 }

rxStatusTable OBJECT-TYPE
	SYNTAX		SEQUENCE OF RxStatusEntry
	MAX-ACCESS	not-accessible
	STATUS		current
	DESCRIPTION "Rx Status Channel Table
			Oid=1.3.6.1.4.1.31968.3.1.4.1.4
			"
	::= { m7xcModemObjs 4 }

rxStatusEntry OBJECT-TYPE
	SYNTAX		RxStatusEntry
	MAX-ACCESS	not-accessible
	STATUS		current
	DESCRIPTION "Rx Status Channel Entry
			Oid=1.3.6.1.4.1.31968.3.1.4.1.4.1
			"
	INDEX {
		rxStatusIndex
	}
	::= { rxStatusTable 1 }

RxStatusEntry ::=
	SEQUENCE {
		rxStatusIndex           Unsigned32,
		rxStatus                INTEGER,
		rxDvbModcod             INTEGER,
		rxLdpcModcod            INTEGER,
		rxEsn0                  Integer32,
		rxMargin                Integer32,
		rxLevel                 Integer32,
		rxLevelImbalance        Integer32,
		rxOffset                Integer32,
		rxOccupied              Unsigned32,
		rxSpectrum              INTEGER,
		rxFrameCount            DisplayString,
		rxFrameErrors           DisplayString,
		rxFrameErrorRate        DisplayString,
		rxRate                  Unsigned32,
		rxAverageRate           Unsigned32,
		rxPps                   Unsigned32,
		rxAveragePps            Unsigned32,
		rxDataPackets           DisplayString,
		rxDataBytes             DisplayString,
		rxIdlePackets           DisplayString,
		rxIdleBytes             DisplayString,
		rxMccPackets            DisplayString,
		rxMccBytes              DisplayString,
		rxAcmPackets            DisplayString,
		rxAcmBytes              DisplayString,
		rxTotalPackets          DisplayString,
		rxTotalBytes            DisplayString,
		rxErredPackets          DisplayString,
		rxTotalPer              DisplayString,
		rxTotalSeconds          Unsigned32,
		rxTotalAverage          Unsigned32,
		rxTotalRate             Unsigned32,
		rxBroadcastRate         Unsigned32,
		rxAverageBroadcastRate  Unsigned32,
		rxBroadcastPps          Unsigned32,
		rxAverageBroadcastPps   Unsigned32,
		rxBroadcastPackets      DisplayString,
		rxBroadcastBytes        DisplayString,
		rxTransecStatus         INTEGER,
		rxMccRate               Unsigned32,
		rxMccAverage            Unsigned32,
		rxAcmRate               Unsigned32,
		rxAcmAverage            Unsigned32,
		rxTransecKeyIndex       Unsigned32,
		rxSnr                   Integer32,
		rxDsssSymbolRate        Unsigned32,
		rxDsssModcod            INTEGER,
		rxAcqSweeps             Unsigned32,
		rxHdrModcod             INTEGER,
		rxFramePeriod           Unsigned32
	}

rxStatusIndex OBJECT-TYPE
	SYNTAX		Unsigned32(1..16)
	MAX-ACCESS	not-accessible
	STATUS		current
	DESCRIPTION "Rx Status Channel Index
			Oid=1.3.6.1.4.1.31968.3.1.4.1.4.1.1
			"
	::= { rxStatusEntry 1 }

rxStatus OBJECT-TYPE
	SYNTAX		INTEGER {
		lockedOk(0),
		lockedOffline(1),
		lockedLowLevelAlarm(2),
		lockedLowEsN0Alarm(3),
		lockedAcmLowModcodLimitAlarm(4),
		lockedDataInactivityAlarm(5),
		lockedTestActive(6),
		lockedDataPortAlarm(7),
		lockedAgcAlarm(8),
		lockedLnbAlarm(9),
		lockedOcxoWarming(10),
		lockedDataUp(11),
		lockedDataUpOffline(12),
		lockedDataUpLowLevelAlarm(13),
		lockedDataUpLowEsN0Alarm(14),
		lockedDataUpAcmLowModcodLimitAlarm(15),
		lockedDataUpDataInactivityAlarm(16),
		lockedDataUpTestActive(17),
		lockedDataUpDataPortAlarm(18),
		lockedDataUpAgcAlarm(19),
		lockedDataUpLnbAlarm(20),
		lockedDataUpOcxoWarming(21),
		lockedDataPendingToGoUp(22),
		lockedDataPendingToGoUpOffline(23),
		lockedDataPendingToGoUpLowLevelAlarm(24),
		lockedDataPendingToGoUpLowEsN0Alarm(25),
		lockedDataPendingToGoUpAcmLowModcodLimitAlarm(26),
		lockedDataPendingToGoUpDataInactivityAlarm(27),
		lockedDataPendingToGoUpTestActive(28),
		lockedDataPendingToGoUpDataPortAlarm(29),
		lockedDataPendingToGoUpAgcAlarm(30),
		lockedDataPendingToGoUpLnbAlarm(31),
		lockedDataPendingToGoUpOcxoWarming(32),
		lockedDataPendingToGoDown(33),
		lockedDataPendingToGoDownOffline(34),
		lockedDataPendingToGoDownLowLevelAlarm(35),
		lockedDataPendingToGoDownLowEsN0Alarm(36),
		lockedDataPendingToGoDownAcmLowModcodLimitAlarm(37),
		lockedDataPendingToGoDownDataInactivityAlarm(38),
		lockedDataPendingToGoDownTestActive(39),
		lockedDataPendingToGoDownDataPortAlarm(40),
		lockedDataPendingToGoDownAgcAlarm(41),
		lockedDataPendingToGoDownLnbAlarm(42),
		lockedDataPendingToGoDownOcxoWarming(43),
		lockedDataDown(44),
		lockedDataDownOffline(45),
		lockedDataDownLowLevelAlarm(46),
		lockedDataDownLowEsN0Alarm(47),
		lockedDataDownAcmLowModcodLimitAlarm(48),
		lockedDataDownDataInactivityAlarm(49),
		lockedDataDownTestActive(50),
		lockedDataDownDataPortAlarm(51),
		lockedDataDownAgcAlarm(52),
		lockedDataDownLnbAlarm(53),
		lockedDataDownOcxoWarming(54),
		lockedEchoLevelImbalance(55),
		lockedOfflineEchoLevelImbalance(56),
		lockedLowLevelAlarmEchoLevelImbalance(57),
		lockedLowEsN0AlarmEchoLevelImbalance(58),
		lockedTestActiveEchoLevelImbalance(59),
		lockedAcmLowModcodLimitAlarmEchoLevelImbalance(60),
		lockedDataInactivityAlarmEchoLevelImbalance(61),
		lockedDataPortAlarmEchoLevelImbalance(62),
		lockedAgcAlarmEchoLevelImbalance(63),
		lockedLnbAlarmEchoLevelImbalance(64),
		lockedEchoLevelImbalanceOcxoWarming(65),
		lockedEchoOffsetImbalance(66),
		lockedOfflineEchoOffsetImbalance(67),
		lockedLowLevelAlarmEchoOffsetImbalance(68),
		lockedLowEsN0AlarmEchoOffsetImbalance(69),
		lockedTestActiveEchoOffsetImbalance(70),
		lockedAcmLowModcodLimitAlarmEchoOffsetImbalance(71),
		lockedDataInactivityAlarmEchoOffsetImbalance(72),
		lockedDataPortAlarmEchoOffsetImbalance(73),
		lockedAgcAlarmEchoOffsetImbalance(74),
		lockedLnbAlarmEchoOffsetImbalance(75),
		lockedEchoOffsetImbalanceOcxoWarming(76),
		unlocked(77),
		unlockedNarrowSweep(78),
		unlockedTestActive(79),
		unlockedDataPortAlarm(80),
		unlockedAgcAlarm(81),
		unlockedLnbAlarm(82),
		unlockedOcxoWarming(83),
		unlockedDataUp(84),
		unlockedDataUpNarrowSweep(85),
		unlockedDataUpTestActive(86),
		unlockedDataUpDataPortAlarm(87),
		unlockedDataUpAgcAlarm(88),
		unlockedDataUpLnbAlarm(89),
		unlockedDataUpOcxoWarming(90),
		unlockedDataPendingUp(91),
		unlockedDataPendingUpNarrowSweep(92),
		unlockedDataPendingUpTestActive(93),
		unlockedDataPendingUpDataPortAlarm(94),
		unlockedDataPendingUpAgcAlarm(95),
		unlockedDataPendingUpLnbAlarm(96),
		unlockedDataPendingUpOcxoWarming(97),
		unlockedDataPendingDown(98),
		unlockedDataPendingDownNarrowSweep(99),
		unlockedDataPendingDownTestActive(100),
		unlockedDataPendingDownDataPortAlarm(101),
		unlockedDataPendingDownAgcAlarm(102),
		unlockedDataPendingDownLnbAlarm(103),
		unlockedDataPendingDownOcxoWarming(104),
		unlockedDataDown(105),
		unlockedDataDownNarrowSweep(106),
		unlockedDataDownTestActive(107),
		unlockedDataDownDataPortAlarm(108),
		unlockedDataDownAgcAlarm(109),
		unlockedDataDownLnbAlarm(110),
		unlockedDataDownOcxoWarming(111),
		unlockedEchoLevelImbalance(112),
		unlockedEchoLevelImbalanceNarrowSweep(113),
		unlockedEchoLevelImbalanceTestActiveEchoLevelImbalance(114),
		unlockedEchoLevelImbalanceDataPortAlarm(115),
		unlockedEchoLevelImbalanceAgcAlarm(116),
		unlockedEchoLevelImbalanceLnbAlarm(117),
		unlockedEchoLevelImbalanceOcxoWarming(118),
		unlockedEchoOffsetImbalance(119),
		unlockedEchoOffsetImbalanceNarrowSweep(120),
		unlockedEchoOffsetImbalanceTestActive(121),
		unlockedEchoOffsetImbalanceDataPortAlarm(122),
		unlockedEchoOffsetImbalanceAgcAlarm(123),
		unlockedEchoOffsetImbalanceLnbAlarm(124),
		unlockedEchoOffsetImbalanceOcxoWarming(125),
		echoUnlocked(126),
		echoUnlockedNarrowSweep(127),
		echoUnlockedTestActive(128),
		echoUnlockedDataPortAlarm(129),
		echoUnlockedAgcAlarm(130),
		echoUnlockedLnbAlarm(131),
		echoUnlockedOcxoWarming(132),
		rxOff(133),
		spectrumAnalyzer(134),
		spectrumAnalyzerLnbAlarm(135),
		spectrumAnalyzerOcxoWarming(136),
		hardwareAlarm(137),
		systemAlarm(138),
		invalidKey(139),
		loadFailed(140),
		overTemperature(141),
		overTemperatureShutdown(142),
		lockedTransecAlarm(143),
		lockedDataUpTransecAlarm(144),
		lockedDataPendingToGoUpTransecAlarm(145),
		lockedDataPendingToGoDownTransecAlarm(146),
		lockedDataDownTransecAlarm(147),
		unlockedTransecAlarm(148),
		lockedTxRxConfigMismatch(149),
		lockedDataUpTxRxConfigMismatch(150),
		lockedDataPendingToGoUpTxRxConfigMismatch(151),
		lockedDataPendingToGoDownTxRxConfigMismatch(152),
		lockedDataDownTxRxConfigMismatch(153),
		totalRxDataRateGreaterThanDataPortLinkRateAlarm(154),
		lockedDataUnbondedAlarm(155),
		lockedAcmTxHubAlarmEchoLevelImbalance(156),
		lockedAcmTxHubAlarmEchoOffsetImbalance(157),
		lockedDataUpAcmTxHubAlarm(158),
		lockedDataDownAcmTxHubAlarm(159),
		lockedAcmTxHubAlarm(160),
		echoUnlockedAcmTxHubAlarm(161),
		unlockedAcmTxHubAlarm(162),
		unlockedEchoLevelImbalanceAcmTxHubAlarm(163),
		unlockedEchoOffsetImbalanceAcmTxHubAlarm(164)
	}
	MAX-ACCESS	read-only
	STATUS		current
	DESCRIPTION "Rx Status, where:
			    0) 'Locked, Ok'
			    1) 'Locked, Offline'
			    2) 'Locked, LOW LEVEL ALARM'
			    3) 'Locked, LOW Es/N0 ALARM'
			    4) 'Locked, ACM LOW MODCOD LIMIT ALARM'
			    5) 'Locked, DATA INACTIVITY ALARM'
			    6) 'Locked, TEST ACTIVE'
			    7) 'Locked, DATA PORT ALARM'
			    8) 'Locked, AGC ALARM'
			    9) 'Locked, LNB ALARM'
			    10) 'Locked, OCXO Warming...'
			    11) 'Locked, Data Up'
			    12) 'Locked, Data Up, Offline'
			    13) 'Locked, Data Up, LOW LEVEL ALARM'
			    14) 'Locked, Data Up, LOW Es/N0 ALARM'
			    15) 'Locked, Data Up, ACM LOW MODCOD LIMIT ALARM'
			    16) 'Locked, Data Up, DATA INACTIVITY ALARM'
			    17) 'Locked, Data Up, TEST ACTIVE'
			    18) 'Locked, Data Up, DATA PORT ALARM'
			    19) 'Locked, Data Up, AGC ALARM'
			    20) 'Locked, Data Up, LNB ALARM'
			    21) 'Locked, Data Up, OCXO Warming...'
			    22) 'Locked, Data Pending To Go Up'
			    23) 'Locked, Data Pending To Go Up, Offline'
			    24) 'Locked, Data Pending To Go Up, LOW LEVEL ALARM'
			    25) 'Locked, Data Pending To Go Up, LOW Es/N0 ALARM'
			    26) 'Locked, Data Pending To Go Up, ACM LOW MODCOD LIMIT ALARM'
			    27) 'Locked, Data Pending To Go Up, DATA INACTIVITY ALARM'
			    28) 'Locked, Data Pending To Go Up, TEST ACTIVE'
			    29) 'Locked, Data Pending To Go Up, DATA PORT ALARM'
			    30) 'Locked, Data Pending To Go Up, AGC ALARM'
			    31) 'Locked, Data Pending To Go Up, LNB ALARM'
			    32) 'Locked, Data Pending To Go Up, OCXO Warming...'
			    33) 'Locked, Data Pending To Go Down'
			    34) 'Locked, Data Pending To Go Down, Offline'
			    35) 'Locked, Data Pending To Go Down, LOW LEVEL ALARM'
			    36) 'Locked, Data Pending To Go Down, LOW Es/N0 ALARM'
			    37) 'Locked, Data Pending To Go Down, ACM LOW MODCOD LIMIT ALARM'
			    38) 'Locked, Data Pending To Go Down, DATA INACTIVITY ALARM'
			    39) 'Locked, Data Pending To Go Down, TEST ACTIVE'
			    40) 'Locked, Data Pending To Go Down, DATA PORT ALARM'
			    41) 'Locked, Data Pending To Go Down, AGC ALARM'
			    42) 'Locked, Data Pending To Go Down, LNB ALARM'
			    43) 'Locked, Data Pending To Go Down, OCXO Warming...'
			    44) 'Locked, Data Down'
			    45) 'Locked, Data Down, Offline'
			    46) 'Locked, Data Down, LOW LEVEL ALARM'
			    47) 'Locked, Data Down, LOW Es/N0 ALARM'
			    48) 'Locked, Data Down, ACM LOW MODCOD LIMIT ALARM'
			    49) 'Locked, Data Down, DATA INACTIVITY ALARM'
			    50) 'Locked, Data Down, TEST ACTIVE'
			    51) 'Locked, Data Down, DATA PORT ALARM'
			    52) 'Locked, Data Down, AGC ALARM'
			    53) 'Locked, Data Down, LNB ALARM'
			    54) 'Locked, Data Down, OCXO Warming...'
			    55) 'Locked, ECHO LEVEL IMBALANCE'
			    56) 'Locked, Offline, ECHO LEVEL IMBALANCE'
			    57) 'Locked, LOW LEVEL ALARM, ECHO LEVEL IMBALANCE'
			    58) 'Locked, LOW Es/N0 ALARM, ECHO LEVEL IMBALANCE'
			    59) 'Locked, TEST ACTIVE, ECHO LEVEL IMBALANCE'
			    60) 'Locked, ACM LOW MODCOD LIMIT ALARM, ECHO LEVEL IMBALANCE'
			    61) 'Locked, DATA INACTIVITY ALARM, ECHO LEVEL IMBALANCE'
			    62) 'Locked, DATA PORT ALARM, ECHO LEVEL IMBALANCE'
			    63) 'Locked, AGC ALARM, ECHO LEVEL IMBALANCE'
			    64) 'Locked, LNB ALARM, ECHO LEVEL IMBALANCE'
			    65) 'Locked, ECHO LEVEL IMBALANCE, OCXO Warming...'
			    66) 'Locked, ECHO OFFSET IMBALANCE'
			    67) 'Locked, Offline, ECHO OFFSET IMBALANCE'
			    68) 'Locked, LOW LEVEL ALARM, ECHO OFFSET IMBALANCE'
			    69) 'Locked, LOW Es/N0 ALARM, ECHO OFFSET IMBALANCE'
			    70) 'Locked, TEST ACTIVE, ECHO OFFSET IMBALANCE'
			    71) 'Locked, ACM LOW MODCOD LIMIT ALARM, ECHO OFFSET IMBALANCE'
			    72) 'Locked, DATA INACTIVITY ALARM, ECHO OFFSET IMBALANCE'
			    73) 'Locked, DATA PORT ALARM, ECHO OFFSET IMBALANCE'
			    74) 'Locked, AGC ALARM, ECHO OFFSET IMBALANCE'
			    75) 'Locked, LNB ALARM, ECHO OFFSET IMBALANCE'
			    76) 'Locked, ECHO OFFSET IMBALANCE, OCXO Warming...'
			    77) 'UNLOCKED'
			    78) 'UNLOCKED, NARROW SWEEP...'
			    79) 'UNLOCKED, TEST ACTIVE'
			    80) 'UNLOCKED, DATA PORT ALARM'
			    81) 'UNLOCKED, AGC ALARM'
			    82) 'UNLOCKED, LNB ALARM'
			    83) 'UNLOCKED, OCXO Warming...'
			    84) 'UNLOCKED, Data Up'
			    85) 'UNLOCKED, Data Up, NARROW SWEEP...'
			    86) 'UNLOCKED, Data Up, TEST ACTIVE'
			    87) 'UNLOCKED, Data Up, DATA PORT ALARM'
			    88) 'UNLOCKED, Data Up, AGC ALARM'
			    89) 'UNLOCKED, Data Up, LNB ALARM'
			    90) 'UNLOCKED, Data Up, OCXO Warming...'
			    91) 'UNLOCKED, Data Pending Up'
			    92) 'UNLOCKED, Data Pending Up, NARROW SWEEP...'
			    93) 'UNLOCKED, Data Pending Up, TEST ACTIVE'
			    94) 'UNLOCKED, Data Pending Up, DATA PORT ALARM'
			    95) 'UNLOCKED, Data Pending Up, AGC ALARM'
			    96) 'UNLOCKED, Data Pending Up, LNB ALARM'
			    97) 'UNLOCKED, Data Pending Up, OCXO Warming...'
			    98) 'UNLOCKED, Data Pending Down'
			    99) 'UNLOCKED, Data Pending Down, NARROW SWEEP...'
			    100) 'UNLOCKED, Data Pending Down, TEST ACTIVE'
			    101) 'UNLOCKED, Data Pending Down, DATA PORT ALARM'
			    102) 'UNLOCKED, Data Pending Down, AGC ALARM'
			    103) 'UNLOCKED, Data Pending Down, LNB ALARM'
			    104) 'UNLOCKED, Data Pending Down, OCXO Warming...'
			    105) 'UNLOCKED, Data Down'
			    106) 'UNLOCKED, Data Down, NARROW SWEEP...'
			    107) 'UNLOCKED, Data Down, TEST ACTIVE'
			    108) 'UNLOCKED, Data Down, DATA PORT ALARM'
			    109) 'UNLOCKED, Data Down, AGC ALARM'
			    110) 'UNLOCKED, Data Down, LNB ALARM'
			    111) 'UNLOCKED, Data Down, OCXO Warming...'
			    112) 'UNLOCKED, ECHO LEVEL IMBALANCE'
			    113) 'UNLOCKED, ECHO LEVEL IMBALANCE, NARROW SWEEP...'
			    114) 'UNLOCKED, ECHO LEVEL IMBALANCE, TEST ACTIVE, ECHO LEVEL IMBALANCE'
			    115) 'UNLOCKED, ECHO LEVEL IMBALANCE, DATA PORT ALARM'
			    116) 'UNLOCKED, ECHO LEVEL IMBALANCE, AGC ALARM'
			    117) 'UNLOCKED, ECHO LEVEL IMBALANCE, LNB ALARM'
			    118) 'UNLOCKED, ECHO LEVEL IMBALANCE, OCXO Warming...'
			    119) 'UNLOCKED, ECHO OFFSET IMBALANCE'
			    120) 'UNLOCKED, ECHO OFFSET IMBALANCE, NARROW SWEEP...'
			    121) 'UNLOCKED, ECHO OFFSET IMBALANCE, TEST ACTIVE'
			    122) 'UNLOCKED, ECHO OFFSET IMBALANCE, DATA PORT ALARM'
			    123) 'UNLOCKED, ECHO OFFSET IMBALANCE, AGC ALARM'
			    124) 'UNLOCKED, ECHO OFFSET IMBALANCE, LNB ALARM'
			    125) 'UNLOCKED, ECHO OFFSET IMBALANCE, OCXO Warming...'
			    126) 'ECHO UNLOCKED'
			    127) 'ECHO UNLOCKED, NARROW SWEEP...'
			    128) 'ECHO UNLOCKED, TEST ACTIVE'
			    129) 'ECHO UNLOCKED, DATA PORT ALARM'
			    130) 'ECHO UNLOCKED, AGC ALARM'
			    131) 'ECHO UNLOCKED, LNB ALARM'
			    132) 'ECHO UNLOCKED, OCXO Warming...'
			    133) 'Rx Off'
			    134) 'Spectrum Analyzer'
			    135) 'Spectrum Analyzer, LNB ALARM'
			    136) 'Spectrum Analyzer, OCXO Warming...'
			    137) 'HARDWARE ALARM'
			    138) 'SYSTEM ALARM'
			    139) 'INVALID KEY'
			    140) 'LOAD FAILED'
			    141) 'OVER TEMPERATURE'
			    142) 'OVER TEMPERATURE SHUTDOWN'
			    143) 'Locked, TRANSEC ALARM'
			    144) 'Locked, Data Up, TRANSEC ALARM'
			    145) 'Locked, Data Pending To Go Up, TRANSEC ALARM'
			    146) 'Locked, Data Pending To Go Down, TRANSEC ALARM'
			    147) 'Locked, Data Down, TRANSEC ALARM'
			    148) 'UNLOCKED, TRANSEC ALARM'
			    149) 'Locked, Tx/Rx CONFIG MISMATCH'
			    150) 'Locked, Data Up, Tx/Rx CONFIG MISMATCH'
			    151) 'Locked, Data Pending To Go Up, Tx/Rx CONFIG MISMATCH'
			    152) 'Locked, Data Pending To Go Down, Tx/Rx CONFIG MISMATCH'
			    153) 'Locked, Data Down, Tx/Rx CONFIG MISMATCH'
			    154) 'TOTAL Rx DATA RATE > DATA PORT LINK RATE ALARM'
			    155) 'Locked, DATA UNBONDED ALARM'
			    156) 'Locked, ACM Tx HUB ALARM, ECHO LEVEL IMBALANCE'
			    157) 'Locked, ACM Tx HUB ALARM, ECHO OFFSET IMBALANCE'
			    158) 'Locked, Data Up, ACM Tx HUB ALARM'
			    159) 'Locked, Data Down, ACM Tx HUB ALARM'
			    160) 'Locked, ACM Tx HUB ALARM'
			    161) 'ECHO UNLOCKED, ACM Tx HUB ALARM'
			    162) 'UNLOCKED, ACM Tx HUB ALARM'
			    163) 'UNLOCKED, ECHO LEVEL IMBALANCE, ACM Tx HUB ALARM'
			    164) 'UNLOCKED, ECHO OFFSET IMBALANCE, ACM Tx HUB ALARM'
			Oid=1.3.6.1.4.1.31968.3.1.4.1.4.1.2
			"
	::= { rxStatusEntry 2 }

rxDvbModcod OBJECT-TYPE
	SYNTAX		INTEGER {
		qpsk1x4Normal(0),
		qpsk1x4NormalWithPilot(1),
		qpsk13x45Normal(2),
		qpsk13x45NormalWithPilot(3),
		qpsk1x3Normal(4),
		qpsk1x3NormalWithPilot(5),
		qpsk2x5Normal(6),
		qpsk2x5NormalWithPilot(7),
		qpsk9x20Normal(8),
		qpsk9x20NormalWithPilot(9),
		qpsk1x2Normal(10),
		qpsk1x2NormalWithPilot(11),
		qpsk11x20Normal(12),
		qpsk11x20NormalWithPilot(13),
		qpsk3x5Normal(14),
		qpsk3x5NormalWithPilot(15),
		qpsk2x3Normal(16),
		qpsk2x3NormalWithPilot(17),
		qpsk3x4Normal(18),
		qpsk3x4NormalWithPilot(19),
		qpsk4x5Normal(20),
		qpsk4x5NormalWithPilot(21),
		qpsk5x6Normal(22),
		qpsk5x6NormalWithPilot(23),
		qpsk8x9Normal(24),
		qpsk8x9NormalWithPilot(25),
		qpsk9x10Normal(26),
		qpsk9x10NormalWithPilot(27),
		n8apsk5x9LNormal(28),
		n8apsk5x9LNormalWithPilot(29),
		n8apsk26x45LNormal(30),
		n8apsk26x45LNormalWithPilot(31),
		n8psk3x5NormalWithPilot(32),
		n8psk23x36Normal(33),
		n8psk23x36NormalWithPilot(34),
		n8psk2x3NormalWithPilot(35),
		n8psk25x36Normal(36),
		n8psk25x36NormalWithPilot(37),
		n8psk13x18Normal(38),
		n8psk13x18NormalWithPilot(39),
		n8psk3x4Normal(40),
		n8psk3x4NormalWithPilot(41),
		n8psk5x6Normal(42),
		n8psk5x6NormalWithPilot(43),
		n8psk8x9Normal(44),
		n8psk8x9NormalWithPilot(45),
		n8psk9x10Normal(46),
		n8psk9x10NormalWithPilot(47),
		n16apsk1x2LNormal(48),
		n16apsk1x2LNormalWithPilot(49),
		n16apsk8x15LNormal(50),
		n16apsk8x15LNormalWithPilot(51),
		n16apsk5x9LNormal(52),
		n16apsk5x9LNormalWithPilot(53),
		n16apsk26x45Normal(54),
		n16apsk26x45NormalWithPilot(55),
		n16apsk3x5Normal(56),
		n16apsk3x5NormalWithPilot(57),
		n16apsk3x5LNormal(58),
		n16apsk3x5LNormalWithPilot(59),
		n16apsk28x45Normal(60),
		n16apsk28x45NormalWithPilot(61),
		n16apsk23x36Normal(62),
		n16apsk23x36NormalWithPilot(63),
		n16apsk2x3LNormal(64),
		n16apsk2x3LNormalWithPilot(65),
		n16apsk2x3Normal(66),
		n16apsk2x3NormalWithPilot(67),
		n16apsk25x36Normal(68),
		n16apsk25x36NormalWithPilot(69),
		n16apsk13x18Normal(70),
		n16apsk13x18NormalWithPilot(71),
		n16apsk3x4NormalWithPilot(72),
		n16apsk7x9Normal(73),
		n16apsk7x9NormalWithPilot(74),
		n16apsk4x5Normal(75),
		n16apsk4x5NormalWithPilot(76),
		n16apsk5x6Normal(77),
		n16apsk5x6NormalWithPilot(78),
		n16apsk77x90Normal(79),
		n16apsk77x90NormalWithPilot(80),
		n16apsk8x9Normal(81),
		n16apsk8x9NormalWithPilot(82),
		n16apsk9x10Normal(83),
		n16apsk9x10NormalWithPilot(84),
		n32apsk2x3LNormal(85),
		n32apsk2x3LNormalWithPilot(86),
		n32apsk32x45Normal(87),
		n32apsk32x45NormalWithPilot(88),
		n32apsk11x15Normal(89),
		n32apsk11x15NormalWithPilot(90),
		n32apsk3x4Normal(91),
		n32apsk3x4NormalWithPilot(92),
		n32apsk7x9Normal(93),
		n32apsk7x9NormalWithPilot(94),
		n32apsk4x5NormalWithPilot(95),
		n32apsk5x6Normal(96),
		n32apsk5x6NormalWithPilot(97),
		n32apsk8x9Normal(98),
		n32apsk8x9NormalWithPilot(99),
		n32apsk9x10Normal(100),
		n32apsk9x10NormalWithPilot(101),
		n64apsk32x45LNormal(102),
		n64apsk32x45LNormalWithPilot(103),
		n64apsk11x15Normal(104),
		n64apsk11x15NormalWithPilot(105),
		n64apsk7x9Normal(106),
		n64apsk7x9NormalWithPilot(107),
		n64apsk4x5Normal(108),
		n64apsk4x5NormalWithPilot(109),
		n64apsk5x6Normal(110),
		n64apsk5x6NormalWithPilot(111),
		n128apsk3x4Normal(112),
		n128apsk3x4NormalWithPilot(113),
		n128apsk7x9Normal(114),
		n128apsk7x9NormalWithPilot(115),
		n256apsk29x45LNormal(116),
		n256apsk29x45LNormalWithPilot(117),
		n256apsk2x3LNormal(118),
		n256apsk2x3LNormalWithPilot(119),
		n256apsk31x45LNormal(120),
		n256apsk31x45LNormalWithPilot(121),
		n256apsk32x45Normal(122),
		n256apsk32x45NormalWithPilot(123),
		n256apsk11x15LNormal(124),
		n256apsk11x15LNormalWithPilot(125),
		n256apsk3x4Normal(126),
		n256apsk3x4NormalWithPilot(127),
		qpsk1x4Short(128),
		qpsk1x4ShortWithPilot(129),
		qpsk11x45Short(130),
		qpsk11x45ShortWithPilot(131),
		qpsk4x15Short(132),
		qpsk4x15ShortWithPilot(133),
		qpsk14x45Short(134),
		qpsk14x45ShortWithPilot(135),
		qpsk1x3Short(136),
		qpsk1x3ShortWithPilot(137),
		qpsk2x5Short(138),
		qpsk2x5ShortWithPilot(139),
		qpsk1x2Short(140),
		qpsk1x2ShortWithPilot(141),
		qpsk7x15Short(142),
		qpsk7x15ShortWithPilot(143),
		qpsk8x15Short(144),
		qpsk8x15ShortWithPilot(145),
		qpsk3x5Short(146),
		qpsk3x5ShortWithPilot(147),
		qpsk2x3Short(148),
		qpsk2x3ShortWithPilot(149),
		qpsk32x45Short(150),
		qpsk32x45ShortWithPilot(151),
		qpsk3x4Short(152),
		qpsk3x4ShortWithPilot(153),
		qpsk4x5Short(154),
		qpsk4x5ShortWithPilot(155),
		qpsk5x6Short(156),
		qpsk5x6ShortWithPilot(157),
		qpsk8x9Short(158),
		qpsk8x9ShortWithPilot(159),
		n8psk7x15Short(160),
		n8psk7x15ShortWithPilot(161),
		n8psk8x15Short(162),
		n8psk8x15ShortWithPilot(163),
		n8psk26x45Short(164),
		n8psk26x45ShortWithPilot(165),
		n8psk3x5ShortWithPilot(166),
		n8psk2x3ShortWithPilot(167),
		n8psk32x45Short(168),
		n8psk32x45ShortWithPilot(169),
		n8psk3x4Short(170),
		n8psk3x4ShortWithPilot(171),
		n8psk5x6Short(172),
		n8psk5x6ShortWithPilot(173),
		n8psk8x9Short(174),
		n8psk8x9ShortWithPilot(175),
		n16apsk7x15Short(176),
		n16apsk7x15ShortWithPilot(177),
		n16apsk8x15Short(178),
		n16apsk8x15ShortWithPilot(179),
		n16apsk26x45Short(180),
		n16apsk26x45ShortWithPilot(181),
		n16apsk3x5Short(182),
		n16apsk3x5ShortWithPilot(183),
		n16apsk2x3Short(184),
		n16apsk2x3ShortWithPilot(185),
		n16apsk32x45Short(186),
		n16apsk32x45ShortWithPilot(187),
		n16apsk3x4ShortWithPilot(188),
		n16apsk4x5Short(189),
		n16apsk4x5ShortWithPilot(190),
		n16apsk5x6Short(191),
		n16apsk5x6ShortWithPilot(192),
		n16apsk8x9Short(193),
		n16apsk8x9ShortWithPilot(194),
		n32apsk2x3Short(195),
		n32apsk2x3ShortWithPilot(196),
		n32apsk32x45Short(197),
		n32apsk32x45ShortWithPilot(198),
		n32apsk3x4Short(199),
		n32apsk3x4ShortWithPilot(200),
		n32apsk4x5ShortWithPilot(201),
		n32apsk5x6Short(202),
		n32apsk5x6ShortWithPilot(203),
		n32apsk8x9Short(204),
		n32apsk8x9ShortWithPilot(205),
		unlocked(206)
	}
	MAX-ACCESS	read-only
	STATUS		current
	DESCRIPTION "Rx ModCod, where:
			    0) 'QPSK 1/4 Normal'
			    1) 'QPSK 1/4 Normal with Pilot'
			    2) 'QPSK 13/45 Normal'
			    3) 'QPSK 13/45 Normal with Pilot'
			    4) 'QPSK 1/3 Normal'
			    5) 'QPSK 1/3 Normal with Pilot'
			    6) 'QPSK 2/5 Normal'
			    7) 'QPSK 2/5 Normal with Pilot'
			    8) 'QPSK 9/20 Normal'
			    9) 'QPSK 9/20 Normal with Pilot'
			    10) 'QPSK 1/2 Normal'
			    11) 'QPSK 1/2 Normal with Pilot'
			    12) 'QPSK 11/20 Normal'
			    13) 'QPSK 11/20 Normal with Pilot'
			    14) 'QPSK 3/5 Normal'
			    15) 'QPSK 3/5 Normal with Pilot'
			    16) 'QPSK 2/3 Normal'
			    17) 'QPSK 2/3 Normal with Pilot'
			    18) 'QPSK 3/4 Normal'
			    19) 'QPSK 3/4 Normal with Pilot'
			    20) 'QPSK 4/5 Normal'
			    21) 'QPSK 4/5 Normal with Pilot'
			    22) 'QPSK 5/6 Normal'
			    23) 'QPSK 5/6 Normal with Pilot'
			    24) 'QPSK 8/9 Normal'
			    25) 'QPSK 8/9 Normal with Pilot'
			    26) 'QPSK 9/10 Normal'
			    27) 'QPSK 9/10 Normal with Pilot'
			    28) '8APSK 5/9-L Normal'
			    29) '8APSK 5/9-L Normal with Pilot'
			    30) '8APSK 26/45-L Normal'
			    31) '8APSK 26/45-L Normal with Pilot'
			    32) '8PSK 3/5 Normal with Pilot'
			    33) '8PSK 23/36 Normal'
			    34) '8PSK 23/36 Normal with Pilot'
			    35) '8PSK 2/3 Normal with Pilot'
			    36) '8PSK 25/36 Normal'
			    37) '8PSK 25/36 Normal with Pilot'
			    38) '8PSK 13/18 Normal'
			    39) '8PSK 13/18 Normal with Pilot'
			    40) '8PSK 3/4 Normal'
			    41) '8PSK 3/4 Normal with Pilot'
			    42) '8PSK 5/6 Normal'
			    43) '8PSK 5/6 Normal with Pilot'
			    44) '8PSK 8/9 Normal'
			    45) '8PSK 8/9 Normal with Pilot'
			    46) '8PSK 9/10 Normal'
			    47) '8PSK 9/10 Normal with Pilot'
			    48) '16APSK 1/2-L Normal'
			    49) '16APSK 1/2-L Normal with Pilot'
			    50) '16APSK 8/15-L Normal'
			    51) '16APSK 8/15-L Normal with Pilot'
			    52) '16APSK 5/9-L Normal'
			    53) '16APSK 5/9-L Normal with Pilot'
			    54) '16APSK 26/45 Normal'
			    55) '16APSK 26/45 Normal with Pilot'
			    56) '16APSK 3/5 Normal'
			    57) '16APSK 3/5 Normal with Pilot'
			    58) '16APSK 3/5-L Normal'
			    59) '16APSK 3/5-L Normal with Pilot'
			    60) '16APSK 28/45 Normal'
			    61) '16APSK 28/45 Normal with Pilot'
			    62) '16APSK 23/36 Normal'
			    63) '16APSK 23/36 Normal with Pilot'
			    64) '16APSK 2/3-L Normal'
			    65) '16APSK 2/3-L Normal with Pilot'
			    66) '16APSK 2/3 Normal'
			    67) '16APSK 2/3 Normal with Pilot'
			    68) '16APSK 25/36 Normal'
			    69) '16APSK 25/36 Normal with Pilot'
			    70) '16APSK 13/18 Normal'
			    71) '16APSK 13/18 Normal with Pilot'
			    72) '16APSK 3/4 Normal with Pilot'
			    73) '16APSK 7/9 Normal'
			    74) '16APSK 7/9 Normal with Pilot'
			    75) '16APSK 4/5 Normal'
			    76) '16APSK 4/5 Normal with Pilot'
			    77) '16APSK 5/6 Normal'
			    78) '16APSK 5/6 Normal with Pilot'
			    79) '16APSK 77/90 Normal'
			    80) '16APSK 77/90 Normal with Pilot'
			    81) '16APSK 8/9 Normal'
			    82) '16APSK 8/9 Normal with Pilot'
			    83) '16APSK 9/10 Normal'
			    84) '16APSK 9/10 Normal with Pilot'
			    85) '32APSK 2/3-L Normal'
			    86) '32APSK 2/3-L Normal with Pilot'
			    87) '32APSK 32/45 Normal'
			    88) '32APSK 32/45 Normal with Pilot'
			    89) '32APSK 11/15 Normal'
			    90) '32APSK 11/15 Normal with Pilot'
			    91) '32APSK 3/4 Normal'
			    92) '32APSK 3/4 Normal with Pilot'
			    93) '32APSK 7/9 Normal'
			    94) '32APSK 7/9 Normal with Pilot'
			    95) '32APSK 4/5 Normal with Pilot'
			    96) '32APSK 5/6 Normal'
			    97) '32APSK 5/6 Normal with Pilot'
			    98) '32APSK 8/9 Normal'
			    99) '32APSK 8/9 Normal with Pilot'
			    100) '32APSK 9/10 Normal'
			    101) '32APSK 9/10 Normal with Pilot'
			    102) '64APSK 32/45-L Normal'
			    103) '64APSK 32/45-L Normal with Pilot'
			    104) '64APSK 11/15 Normal'
			    105) '64APSK 11/15 Normal with Pilot'
			    106) '64APSK 7/9 Normal'
			    107) '64APSK 7/9 Normal with Pilot'
			    108) '64APSK 4/5 Normal'
			    109) '64APSK 4/5 Normal with Pilot'
			    110) '64APSK 5/6 Normal'
			    111) '64APSK 5/6 Normal with Pilot'
			    112) '128APSK 3/4 Normal'
			    113) '128APSK 3/4 Normal with Pilot'
			    114) '128APSK 7/9 Normal'
			    115) '128APSK 7/9 Normal with Pilot'
			    116) '256APSK 29/45-L Normal'
			    117) '256APSK 29/45-L Normal with Pilot'
			    118) '256APSK 2/3-L Normal'
			    119) '256APSK 2/3-L Normal with Pilot'
			    120) '256APSK 31/45-L Normal'
			    121) '256APSK 31/45-L Normal with Pilot'
			    122) '256APSK 32/45 Normal'
			    123) '256APSK 32/45 Normal with Pilot'
			    124) '256APSK 11/15-L Normal'
			    125) '256APSK 11/15-L Normal with Pilot'
			    126) '256APSK 3/4 Normal'
			    127) '256APSK 3/4 Normal with Pilot'
			    128) 'QPSK 1/4 Short'
			    129) 'QPSK 1/4 Short with Pilot'
			    130) 'QPSK 11/45 Short'
			    131) 'QPSK 11/45 Short with Pilot'
			    132) 'QPSK 4/15 Short'
			    133) 'QPSK 4/15 Short with Pilot'
			    134) 'QPSK 14/45 Short'
			    135) 'QPSK 14/45 Short with Pilot'
			    136) 'QPSK 1/3 Short'
			    137) 'QPSK 1/3 Short with Pilot'
			    138) 'QPSK 2/5 Short'
			    139) 'QPSK 2/5 Short with Pilot'
			    140) 'QPSK 1/2 Short'
			    141) 'QPSK 1/2 Short with Pilot'
			    142) 'QPSK 7/15 Short'
			    143) 'QPSK 7/15 Short with Pilot'
			    144) 'QPSK 8/15 Short'
			    145) 'QPSK 8/15 Short with Pilot'
			    146) 'QPSK 3/5 Short'
			    147) 'QPSK 3/5 Short with Pilot'
			    148) 'QPSK 2/3 Short'
			    149) 'QPSK 2/3 Short with Pilot'
			    150) 'QPSK 32/45 Short'
			    151) 'QPSK 32/45 Short with Pilot'
			    152) 'QPSK 3/4 Short'
			    153) 'QPSK 3/4 Short with Pilot'
			    154) 'QPSK 4/5 Short'
			    155) 'QPSK 4/5 Short with Pilot'
			    156) 'QPSK 5/6 Short'
			    157) 'QPSK 5/6 Short with Pilot'
			    158) 'QPSK 8/9 Short'
			    159) 'QPSK 8/9 Short with Pilot'
			    160) '8PSK 7/15 Short'
			    161) '8PSK 7/15 Short with Pilot'
			    162) '8PSK 8/15 Short'
			    163) '8PSK 8/15 Short with Pilot'
			    164) '8PSK 26/45 Short'
			    165) '8PSK 26/45 Short with Pilot'
			    166) '8PSK 3/5 Short with Pilot'
			    167) '8PSK 2/3 Short with Pilot'
			    168) '8PSK 32/45 Short'
			    169) '8PSK 32/45 Short with Pilot'
			    170) '8PSK 3/4 Short'
			    171) '8PSK 3/4 Short with Pilot'
			    172) '8PSK 5/6 Short'
			    173) '8PSK 5/6 Short with Pilot'
			    174) '8PSK 8/9 Short'
			    175) '8PSK 8/9 Short with Pilot'
			    176) '16APSK 7/15 Short'
			    177) '16APSK 7/15 Short with Pilot'
			    178) '16APSK 8/15 Short'
			    179) '16APSK 8/15 Short with Pilot'
			    180) '16APSK 26/45 Short'
			    181) '16APSK 26/45 Short with Pilot'
			    182) '16APSK 3/5 Short'
			    183) '16APSK 3/5 Short with Pilot'
			    184) '16APSK 2/3 Short'
			    185) '16APSK 2/3 Short with Pilot'
			    186) '16APSK 32/45 Short'
			    187) '16APSK 32/45 Short with Pilot'
			    188) '16APSK 3/4 Short with Pilot'
			    189) '16APSK 4/5 Short'
			    190) '16APSK 4/5 Short with Pilot'
			    191) '16APSK 5/6 Short'
			    192) '16APSK 5/6 Short with Pilot'
			    193) '16APSK 8/9 Short'
			    194) '16APSK 8/9 Short with Pilot'
			    195) '32APSK 2/3 Short'
			    196) '32APSK 2/3 Short with Pilot'
			    197) '32APSK 32/45 Short'
			    198) '32APSK 32/45 Short with Pilot'
			    199) '32APSK 3/4 Short'
			    200) '32APSK 3/4 Short with Pilot'
			    201) '32APSK 4/5 Short with Pilot'
			    202) '32APSK 5/6 Short'
			    203) '32APSK 5/6 Short with Pilot'
			    204) '32APSK 8/9 Short'
			    205) '32APSK 8/9 Short with Pilot'
			    206) 'Unlocked'
			Oid=1.3.6.1.4.1.31968.3.1.4.1.4.1.3
			"
	::= { rxStatusEntry 3 }

rxLdpcModcod OBJECT-TYPE
	SYNTAX		INTEGER {
		bpsk1x2(0),
		bpsk8x15(1),
		bpsk4x7(2),
		bpsk8x13(3),
		bpsk2x3(4),
		bpsk16x23(5),
		bpsk8x11(6),
		qpsk1x2(7),
		qpsk8x15(8),
		qpsk4x7(9),
		qpsk8x13(10),
		qpsk2x3(11),
		qpsk16x23(12),
		qpsk8x11(13),
		qpsk16x21(14),
		qpsk4x5(15),
		qpsk16x19(16),
		qpsk8x9(17),
		n8psk8x13(18),
		n8psk2x3(19),
		n8psk16x23(20),
		n8apsk8x13(21),
		n8apsk2x3(22),
		n8apsk16x23(23),
		n16apsk4x7(24),
		n16apsk8x13(25),
		n16apsk2x3(26),
		n16apsk16x23(27),
		n16apsk8x11(28),
		n16apsk16x21(29),
		n16apsk4x5(30),
		n16apsk16x19(31),
		n16apsk8x9(32),
		n16apsk16x17(33),
		n16qam1x2(34),
		n16qam8x15(35),
		n16qam4x7(36),
		n16qam8x13(37),
		n16qam2x3(38),
		n16qam16x23(39),
		n16qam8x11(40),
		n16qam16x21(41),
		n16qam4x5(42),
		n16qam16x19(43),
		n16qam8x9(44),
		n16qam16x17(45),
		n32qam2x3(46),
		n32qam16x23(47),
		n32qam8x11(48),
		n32qam16x21(49),
		n32qam4x5(50),
		n32qam16x19(51),
		n32qam8x9(52),
		n32qam16x17(53),
		n64qam2x3(54),
		n64qam16x23(55),
		n64qam8x11(56),
		n64qam16x21(57),
		n64qam4x5(58),
		n64qam16x19(59),
		n64qam8x9(60),
		n64qam16x17(61),
		idleData(62),
		unlocked(128)
	}
	MAX-ACCESS	read-only
	STATUS		current
	DESCRIPTION "Rx ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'QPSK 1/2'
			    8) 'QPSK 8/15'
			    9) 'QPSK 4/7'
			    10) 'QPSK 8/13'
			    11) 'QPSK 2/3'
			    12) 'QPSK 16/23'
			    13) 'QPSK 8/11'
			    14) 'QPSK 16/21'
			    15) 'QPSK 4/5'
			    16) 'QPSK 16/19'
			    17) 'QPSK 8/9'
			    18) '8PSK 8/13'
			    19) '8PSK 2/3'
			    20) '8PSK 16/23'
			    21) '8APSK 8/13'
			    22) '8APSK 2/3'
			    23) '8APSK 16/23'
			    24) '16APSK 4/7'
			    25) '16APSK 8/13'
			    26) '16APSK 2/3'
			    27) '16APSK 16/23'
			    28) '16APSK 8/11'
			    29) '16APSK 16/21'
			    30) '16APSK 4/5'
			    31) '16APSK 16/19'
			    32) '16APSK 8/9'
			    33) '16APSK 16/17'
			    34) '16QAM 1/2'
			    35) '16QAM 8/15'
			    36) '16QAM 4/7'
			    37) '16QAM 8/13'
			    38) '16QAM 2/3'
			    39) '16QAM 16/23'
			    40) '16QAM 8/11'
			    41) '16QAM 16/21'
			    42) '16QAM 4/5'
			    43) '16QAM 16/19'
			    44) '16QAM 8/9'
			    45) '16QAM 16/17'
			    46) '32QAM 2/3'
			    47) '32QAM 16/23'
			    48) '32QAM 8/11'
			    49) '32QAM 16/21'
			    50) '32QAM 4/5'
			    51) '32QAM 16/19'
			    52) '32QAM 8/9'
			    53) '32QAM 16/17'
			    54) '64QAM 2/3'
			    55) '64QAM 16/23'
			    56) '64QAM 8/11'
			    57) '64QAM 16/21'
			    58) '64QAM 4/5'
			    59) '64QAM 16/19'
			    60) '64QAM 8/9'
			    61) '64QAM 16/17'
			    62) 'Idle Data'
			    128) 'Unlocked'
			Oid=1.3.6.1.4.1.31968.3.1.4.1.4.1.4
			"
	::= { rxStatusEntry 4 }

rxEsn0 OBJECT-TYPE
	SYNTAX		Integer32
	UNITS		"0.01 dB"
	MAX-ACCESS	read-only
	STATUS		current
	DESCRIPTION "Rx Es/N0
			Oid=1.3.6.1.4.1.31968.3.1.4.1.4.1.5
			"
	::= { rxStatusEntry 5 }

rxMargin OBJECT-TYPE
	SYNTAX		Integer32
	UNITS		"0.01 dB"
	MAX-ACCESS	read-only
	STATUS		current
	DESCRIPTION "Rx QEF Margin
			Oid=1.3.6.1.4.1.31968.3.1.4.1.4.1.6
			"
	::= { rxStatusEntry 6 }

rxLevel OBJECT-TYPE
	SYNTAX		Integer32
	UNITS		"0.01 dBm"
	MAX-ACCESS	read-only
	STATUS		current
	DESCRIPTION "Rx Level
			Oid=1.3.6.1.4.1.31968.3.1.4.1.4.1.7
			"
	::= { rxStatusEntry 7 }

rxLevelImbalance OBJECT-TYPE
	SYNTAX		Integer32
	UNITS		"0.01 dB"
	MAX-ACCESS	read-only
	STATUS		current
	DESCRIPTION "Rx Level Imbalance
			Oid=1.3.6.1.4.1.31968.3.1.4.1.4.1.8
			"
	::= { rxStatusEntry 8 }

rxOffset OBJECT-TYPE
	SYNTAX		Integer32
	UNITS		"1 Hz"
	MAX-ACCESS	read-only
	STATUS		current
	DESCRIPTION "Rx Offset
			Oid=1.3.6.1.4.1.31968.3.1.4.1.4.1.9
			"
	::= { rxStatusEntry 9 }

rxOccupied OBJECT-TYPE
	SYNTAX		Unsigned32
	UNITS		"1 Hz"
	MAX-ACCESS	read-only
	STATUS		current
	DESCRIPTION "Rx Occupied Bandwidth
			Oid=1.3.6.1.4.1.31968.3.1.4.1.4.1.10
			"
	::= { rxStatusEntry 10 }

rxSpectrum OBJECT-TYPE
	SYNTAX		INTEGER {
		normal(0),
		inverted(1)
	}
	MAX-ACCESS	read-only
	STATUS		current
	DESCRIPTION "Rx Spectrum, where:
			    0) 'Normal'
			    1) 'Inverted'
			Oid=1.3.6.1.4.1.31968.3.1.4.1.4.1.11
			"
	::= { rxStatusEntry 11 }

rxFrameCount OBJECT-TYPE
	SYNTAX		DisplayString(SIZE(1..24))
	UNITS		"1"
	MAX-ACCESS	read-only
	STATUS		current
	DESCRIPTION "Rx Frame Count,
			    Text Number, Decimal
			Oid=1.3.6.1.4.1.31968.3.1.4.1.4.1.12
			"
	::= { rxStatusEntry 12 }

rxFrameErrors OBJECT-TYPE
	SYNTAX		DisplayString(SIZE(1..24))
	UNITS		"1"
	MAX-ACCESS	read-only
	STATUS		current
	DESCRIPTION "Rx Frame Errors,
			    Text Number, Decimal
			Oid=1.3.6.1.4.1.31968.3.1.4.1.4.1.13
			"
	::= { rxStatusEntry 13 }

rxFrameErrorRate OBJECT-TYPE
	SYNTAX		DisplayString(SIZE(1..12))
	MAX-ACCESS	read-only
	STATUS		current
	DESCRIPTION "Rx Frame Error Rate,
			    Text Number, Decimal Floating Point
			Oid=1.3.6.1.4.1.31968.3.1.4.1.4.1.14
			"
	::= { rxStatusEntry 14 }

rxRate OBJECT-TYPE
	SYNTAX		Unsigned32
	UNITS		"1 bps"
	MAX-ACCESS	read-only
	STATUS		current
	DESCRIPTION "Rx Data Rate
			Oid=1.3.6.1.4.1.31968.3.1.4.1.4.1.15
			"
	::= { rxStatusEntry 15 }

rxAverageRate OBJECT-TYPE
	SYNTAX		Unsigned32
	UNITS		"1 bps"
	MAX-ACCESS	read-only
	STATUS		current
	DESCRIPTION "Rx Average Data Rate
			Oid=1.3.6.1.4.1.31968.3.1.4.1.4.1.16
			"
	::= { rxStatusEntry 16 }

rxPps OBJECT-TYPE
	SYNTAX		Unsigned32
	UNITS		"1 pps"
	MAX-ACCESS	read-only
	STATUS		current
	DESCRIPTION "Rx Data PPS
			Oid=1.3.6.1.4.1.31968.3.1.4.1.4.1.17
			"
	::= { rxStatusEntry 17 }

rxAveragePps OBJECT-TYPE
	SYNTAX		Unsigned32
	UNITS		"1 pps"
	MAX-ACCESS	read-only
	STATUS		current
	DESCRIPTION "Rx Average Data PPS
			Oid=1.3.6.1.4.1.31968.3.1.4.1.4.1.18
			"
	::= { rxStatusEntry 18 }

rxDataPackets OBJECT-TYPE
	SYNTAX		DisplayString(SIZE(1..24))
	UNITS		"1"
	MAX-ACCESS	read-only
	STATUS		current
	DESCRIPTION "Rx Data Packets,
			    Text Number, Decimal
			Oid=1.3.6.1.4.1.31968.3.1.4.1.4.1.19
			"
	::= { rxStatusEntry 19 }

rxDataBytes OBJECT-TYPE
	SYNTAX		DisplayString(SIZE(1..24))
	UNITS		"1"
	MAX-ACCESS	read-only
	STATUS		current
	DESCRIPTION "Rx Data Bytes,
			    Text Number, Decimal
			Oid=1.3.6.1.4.1.31968.3.1.4.1.4.1.20
			"
	::= { rxStatusEntry 20 }

rxIdlePackets OBJECT-TYPE
	SYNTAX		DisplayString(SIZE(1..24))
	UNITS		"1"
	MAX-ACCESS	read-only
	STATUS		current
	DESCRIPTION "Rx Idle Packets,
			    Text Number, Decimal
			Oid=1.3.6.1.4.1.31968.3.1.4.1.4.1.21
			"
	::= { rxStatusEntry 21 }

rxIdleBytes OBJECT-TYPE
	SYNTAX		DisplayString(SIZE(1..24))
	UNITS		"1"
	MAX-ACCESS	read-only
	STATUS		current
	DESCRIPTION "Rx Idle Bytes,
			    Text Number, Decimal
			Oid=1.3.6.1.4.1.31968.3.1.4.1.4.1.22
			"
	::= { rxStatusEntry 22 }

rxMccPackets OBJECT-TYPE
	SYNTAX		DisplayString(SIZE(1..24))
	UNITS		"1"
	MAX-ACCESS	read-only
	STATUS		current
	DESCRIPTION "Rx MCC Packets,
			    Text Number, Decimal
			Oid=1.3.6.1.4.1.31968.3.1.4.1.4.1.23
			"
	::= { rxStatusEntry 23 }

rxMccBytes OBJECT-TYPE
	SYNTAX		DisplayString(SIZE(1..24))
	UNITS		"1"
	MAX-ACCESS	read-only
	STATUS		current
	DESCRIPTION "Rx MCC Bytes,
			    Text Number, Decimal
			Oid=1.3.6.1.4.1.31968.3.1.4.1.4.1.24
			"
	::= { rxStatusEntry 24 }

rxAcmPackets OBJECT-TYPE
	SYNTAX		DisplayString(SIZE(1..24))
	UNITS		"1"
	MAX-ACCESS	read-only
	STATUS		current
	DESCRIPTION "Rx ACM/AUPC Packets,
			    Text Number, Decimal
			Oid=1.3.6.1.4.1.31968.3.1.4.1.4.1.25
			"
	::= { rxStatusEntry 25 }

rxAcmBytes OBJECT-TYPE
	SYNTAX		DisplayString(SIZE(1..24))
	UNITS		"1"
	MAX-ACCESS	read-only
	STATUS		current
	DESCRIPTION "Rx ACM/AUPC Bytes,
			    Text Number, Decimal
			Oid=1.3.6.1.4.1.31968.3.1.4.1.4.1.26
			"
	::= { rxStatusEntry 26 }

rxTotalPackets OBJECT-TYPE
	SYNTAX		DisplayString(SIZE(1..24))
	UNITS		"1"
	MAX-ACCESS	read-only
	STATUS		current
	DESCRIPTION "Rx Total Packets,
			    Text Number, Decimal
			Oid=1.3.6.1.4.1.31968.3.1.4.1.4.1.27
			"
	::= { rxStatusEntry 27 }

rxTotalBytes OBJECT-TYPE
	SYNTAX		DisplayString(SIZE(1..24))
	UNITS		"1"
	MAX-ACCESS	read-only
	STATUS		current
	DESCRIPTION "Rx Total Bytes,
			    Text Number, Decimal
			Oid=1.3.6.1.4.1.31968.3.1.4.1.4.1.28
			"
	::= { rxStatusEntry 28 }

rxErredPackets OBJECT-TYPE
	SYNTAX		DisplayString(SIZE(1..24))
	UNITS		"1"
	MAX-ACCESS	read-only
	STATUS		current
	DESCRIPTION "Rx Erred Packets,
			    Text Number, Decimal
			Oid=1.3.6.1.4.1.31968.3.1.4.1.4.1.29
			"
	::= { rxStatusEntry 29 }

rxTotalPer OBJECT-TYPE
	SYNTAX		DisplayString(SIZE(1..12))
	MAX-ACCESS	read-only
	STATUS		current
	DESCRIPTION "Rx Total PER,
			    Text Number, Decimal Floating Point
			Oid=1.3.6.1.4.1.31968.3.1.4.1.4.1.30
			"
	::= { rxStatusEntry 30 }

rxTotalSeconds OBJECT-TYPE
	SYNTAX		Unsigned32
	UNITS		"1 s"
	MAX-ACCESS	read-only
	STATUS		current
	DESCRIPTION "Rx Total Seconds
			Oid=1.3.6.1.4.1.31968.3.1.4.1.4.1.31
			"
	::= { rxStatusEntry 31 }

rxTotalAverage OBJECT-TYPE
	SYNTAX		Unsigned32
	UNITS		"1 bps"
	MAX-ACCESS	read-only
	STATUS		current
	DESCRIPTION "Rx Average Total Rate
			Oid=1.3.6.1.4.1.31968.3.1.4.1.4.1.32
			"
	::= { rxStatusEntry 32 }

rxTotalRate OBJECT-TYPE
	SYNTAX		Unsigned32
	UNITS		"1 bps"
	MAX-ACCESS	read-only
	STATUS		current
	DESCRIPTION "Rx Total Rate
			Oid=1.3.6.1.4.1.31968.3.1.4.1.4.1.33
			"
	::= { rxStatusEntry 33 }

rxBroadcastRate OBJECT-TYPE
	SYNTAX		Unsigned32
	UNITS		"1 bps"
	MAX-ACCESS	read-only
	STATUS		current
	DESCRIPTION "Rx Broadcast Rate
			Oid=1.3.6.1.4.1.31968.3.1.4.1.4.1.34
			"
	::= { rxStatusEntry 34 }

rxAverageBroadcastRate OBJECT-TYPE
	SYNTAX		Unsigned32
	UNITS		"1 bps"
	MAX-ACCESS	read-only
	STATUS		current
	DESCRIPTION "Rx Average Broadcast Rate
			Oid=1.3.6.1.4.1.31968.3.1.4.1.4.1.35
			"
	::= { rxStatusEntry 35 }

rxBroadcastPps OBJECT-TYPE
	SYNTAX		Unsigned32
	UNITS		"1 pps"
	MAX-ACCESS	read-only
	STATUS		current
	DESCRIPTION "Rx Broadcast PPS
			Oid=1.3.6.1.4.1.31968.3.1.4.1.4.1.36
			"
	::= { rxStatusEntry 36 }

rxAverageBroadcastPps OBJECT-TYPE
	SYNTAX		Unsigned32
	UNITS		"1 pps"
	MAX-ACCESS	read-only
	STATUS		current
	DESCRIPTION "Rx Average Broadcast PPS
			Oid=1.3.6.1.4.1.31968.3.1.4.1.4.1.37
			"
	::= { rxStatusEntry 37 }

rxBroadcastPackets OBJECT-TYPE
	SYNTAX		DisplayString(SIZE(1..24))
	UNITS		"1"
	MAX-ACCESS	read-only
	STATUS		current
	DESCRIPTION "Rx Broadcast Packets,
			    Text Number, Decimal
			Oid=1.3.6.1.4.1.31968.3.1.4.1.4.1.38
			"
	::= { rxStatusEntry 38 }

rxBroadcastBytes OBJECT-TYPE
	SYNTAX		DisplayString(SIZE(1..24))
	UNITS		"1"
	MAX-ACCESS	read-only
	STATUS		current
	DESCRIPTION "Rx Broadcast Bytes,
			    Text Number, Decimal
			Oid=1.3.6.1.4.1.31968.3.1.4.1.4.1.39
			"
	::= { rxStatusEntry 39 }

rxTransecStatus OBJECT-TYPE
	SYNTAX		INTEGER {
		notInstalled(0),
		temperatureAlarm(1),
		hardwareAlarm(2),
		selfTestFailure(3),
		notOperational(4),
		coIdentifierKeysZeroizedLogAsterisk(10),
		keyNotInitializedLogAsterisk(11),
		dataNotEncryptedLogAsterisk(12),
		errorKeyIndexInvalidLogAsterisk(13),
		errorKeyIndexExpiredLogAsterisk(14),
		keyMismatchLogAsterisk(15),
		dataEncryptedLogAsterisk(16),
		coIdentifierKeysZeroized(20),
		keyNotInitialized(21),
		dataNotEncrypted(22),
		errorKeyIndexInvalid(23),
		errorKeyIndexExpired(24),
		keyMismatch(25),
		dataEncrypted(26)
	}
	MAX-ACCESS	read-only
	STATUS		current
	DESCRIPTION "Rx Status, where:
			    0) 'Not Installed'
			    1) 'TEMPERATURE ALARM'
			    2) 'HARDWARE ALARM'
			    3) 'SELF TEST FAILURE'
			    4) 'NOT OPERATIONAL'
			    10) 'CO Identifier/Keys Zeroized, Log*'
			    11) 'KEY NOT INITIALIZED, Log*'
			    12) 'DATA NOT ENCRYPTED, Log*'
			    13) 'ERROR, KEY INDEX INVALID, Log*'
			    14) 'ERROR, KEY INDEX EXPIRED, Log*'
			    15) 'KEY MISMATCH, Log*'
			    16) 'Data Encrypted, Log*'
			    20) 'CO Identifier/Keys Zeroized'
			    21) 'KEY NOT INITIALIZED'
			    22) 'DATA NOT ENCRYPTED'
			    23) 'ERROR, KEY INDEX INVALID'
			    24) 'ERROR, KEY INDEX EXPIRED'
			    25) 'KEY MISMATCH'
			    26) 'Data Encrypted'
			Oid=1.3.6.1.4.1.31968.3.1.4.1.4.1.42
			"
	::= { rxStatusEntry 42 }

rxMccRate OBJECT-TYPE
	SYNTAX		Unsigned32
	UNITS		"1 bps"
	MAX-ACCESS	read-only
	STATUS		current
	DESCRIPTION "Rx MCC Rate
			Oid=1.3.6.1.4.1.31968.3.1.4.1.4.1.43
			"
	::= { rxStatusEntry 43 }

rxMccAverage OBJECT-TYPE
	SYNTAX		Unsigned32
	UNITS		"1 bps"
	MAX-ACCESS	read-only
	STATUS		current
	DESCRIPTION "Rx Average MCC Rate
			Oid=1.3.6.1.4.1.31968.3.1.4.1.4.1.44
			"
	::= { rxStatusEntry 44 }

rxAcmRate OBJECT-TYPE
	SYNTAX		Unsigned32
	UNITS		"1 bps"
	MAX-ACCESS	read-only
	STATUS		current
	DESCRIPTION "Rx ACM/AUPC Rate
			Oid=1.3.6.1.4.1.31968.3.1.4.1.4.1.45
			"
	::= { rxStatusEntry 45 }

rxAcmAverage OBJECT-TYPE
	SYNTAX		Unsigned32
	UNITS		"1 bps"
	MAX-ACCESS	read-only
	STATUS		current
	DESCRIPTION "Rx Average ACM/AUPC Rate
			Oid=1.3.6.1.4.1.31968.3.1.4.1.4.1.46
			"
	::= { rxStatusEntry 46 }

rxTransecKeyIndex OBJECT-TYPE
	SYNTAX		Unsigned32
	UNITS		"1"
	MAX-ACCESS	read-only
	STATUS		current
	DESCRIPTION "Rx Key Index
			Oid=1.3.6.1.4.1.31968.3.1.4.1.4.1.47
			"
	::= { rxStatusEntry 47 }

rxSnr OBJECT-TYPE
	SYNTAX		Integer32
	UNITS		"0.01 dB"
	MAX-ACCESS	read-only
	STATUS		current
	DESCRIPTION "Rx SNR
			Oid=1.3.6.1.4.1.31968.3.1.4.1.4.1.48
			"
	::= { rxStatusEntry 48 }

rxDsssSymbolRate OBJECT-TYPE
	SYNTAX		Unsigned32
	UNITS		"1 sps"
	MAX-ACCESS	read-only
	STATUS		current
	DESCRIPTION "Rx Despread Symbol Rate
			Oid=1.3.6.1.4.1.31968.3.1.4.1.4.1.49
			"
	::= { rxStatusEntry 49 }

rxDsssModcod OBJECT-TYPE
	SYNTAX		INTEGER {
		bpsk1x2(0),
		bpsk8x15(1),
		bpsk4x7(2),
		bpsk8x13(3),
		bpsk2x3(4),
		bpsk16x23(5),
		bpsk8x11(6),
		bpsk16x21(7),
		bpsk4x5(8),
		bpsk16x19(9),
		bpsk8x9(10)
	}
	MAX-ACCESS	read-only
	STATUS		current
	DESCRIPTION "Rx ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'BPSK 16/21'
			    8) 'BPSK 4/5'
			    9) 'BPSK 16/19'
			    10) 'BPSK 8/9'
			Oid=1.3.6.1.4.1.31968.3.1.4.1.4.1.50
			"
	::= { rxStatusEntry 50 }

rxAcqSweeps OBJECT-TYPE
	SYNTAX		Unsigned32
	UNITS		"1"
	MAX-ACCESS	read-only
	STATUS		current
	DESCRIPTION "Rx Acquistion Sweeps
			Oid=1.3.6.1.4.1.31968.3.1.4.1.4.1.51
			"
	::= { rxStatusEntry 51 }

rxHdrModcod OBJECT-TYPE
	SYNTAX		INTEGER {
		fr80t5x4L8(0),
		fr80t5x4L7(1),
		fr80t5x4L6(2),
		fr80t5x4L5(3),
		fr80t5x4L4(4),
		fr80t5x4L3(5),
		fr80t5x4L2(6),
		fr80t5x4L1(7),
		fr80t5x16L3(8),
		fr80t5x16L2(9),
		fr80t5x16L1(10),
		fr80t5x16R(11),
		fr80t5x16H1(12),
		fr80t5x16H2(13),
		fr80t5x16H3(14),
		fr80t5x16H4(15),
		fr80t5x16H5(16),
		fr80t5x16H6(17),
		fr80t5x32H1(18),
		fr80t5x32H2(19),
		fr80t5x32H3(20),
		fr80t5x32H4(21),
		fr80t5x32H5(22),
		fr80t5x32H6(23),
		fr80t5x64R(24),
		fr80t5x64H1(25),
		fr80t5x64H2(26),
		fr80t5x64H3(27),
		fr80t5x64H4(28),
		fr80t5x64H5(29),
		fr80t5x64H6(30),
		unlocked(31)
	}
	MAX-ACCESS	read-only
	STATUS		current
	DESCRIPTION "Rx ModCod, where:
			    0) 'FR80T5X4-L8'
			    1) 'FR80T5X4-L7'
			    2) 'FR80T5X4-L6'
			    3) 'FR80T5X4-L5'
			    4) 'FR80T5X4-L4'
			    5) 'FR80T5X4-L3'
			    6) 'FR80T5X4-L2'
			    7) 'FR80T5X4-L1'
			    8) 'FR80T5X16-L3'
			    9) 'FR80T5X16-L2'
			    10) 'FR80T5X16-L1'
			    11) 'FR80T5X16-R'
			    12) 'FR80T5X16-H1'
			    13) 'FR80T5X16-H2'
			    14) 'FR80T5X16-H3'
			    15) 'FR80T5X16-H4'
			    16) 'FR80T5X16-H5'
			    17) 'FR80T5X16-H6'
			    18) 'FR80T5X32-H1'
			    19) 'FR80T5X32-H2'
			    20) 'FR80T5X32-H3'
			    21) 'FR80T5X32-H4'
			    22) 'FR80T5X32-H5'
			    23) 'FR80T5X32-H6'
			    24) 'FR80T5X64-R'
			    25) 'FR80T5X64-H1'
			    26) 'FR80T5X64-H2'
			    27) 'FR80T5X64-H3'
			    28) 'FR80T5X64-H4'
			    29) 'FR80T5X64-H5'
			    30) 'FR80T5X64-H6'
			    31) 'Unlocked'
			Oid=1.3.6.1.4.1.31968.3.1.4.1.4.1.52
			"
	::= { rxStatusEntry 52 }

rxFramePeriod OBJECT-TYPE
	SYNTAX		Unsigned32
	UNITS		"0.01 ms"
	MAX-ACCESS	read-only
	STATUS		current
	DESCRIPTION "Rx Frame Period
			Oid=1.3.6.1.4.1.31968.3.1.4.1.4.1.53
			"
	::= { rxStatusEntry 53 }

rxWaveform OBJECT-TYPE
	SYNTAX		INTEGER {
		rxOff(0),
		dvbS2x(1),
		dvbS2xWithSmartCarrier(2),
		ldpcGen2(3),
		ldpcGen2WithSmartCarrier(4),
		ldpcGen2HubWithSmartCarrier(5),
		segmentedLdpcGen2(6),
		ldpcHdlc(7),
		ldpcHdlcWithSmartCarrier(8),
		spectrumAnalyzer(9),
		dvbS2xVcm(10),
		mil165bDvbS2x(11),
		dsssLdpcGen2(12),
		hdrTurbo(13)
	}
	MAX-ACCESS	read-write
	STATUS		current
	DESCRIPTION "Rx Waveform, where:
			    0) 'Rx Off'
			    1) 'DVB-S2X'
			    2) 'DVB-S2X with Smart Carrier'
			    3) 'LDPC-Gen2'
			    4) 'LDPC-Gen2 with Smart Carrier'
			    5) 'LDPC-Gen2 Hub with Smart Carrier'
			    6) 'Segmented LDPC-Gen2'
			    7) 'LDPC HDLC'
			    8) 'LDPC HDLC with Smart Carrier'
			    9) 'Spectrum Analyzer'
			    10) 'DVB-S2X VCM'
			    11) 'MIL 165B DVB-S2X'
			    12) 'DSSS LDPC-Gen2'
			    13) 'HDR Turbo'
			Oid=1.3.6.1.4.1.31968.3.1.4.1.5.1
			"
	::= { rxConfigItems 1 }

rxTotalChannels OBJECT-TYPE
	SYNTAX		Unsigned32
	UNITS		"1"
	MAX-ACCESS	read-write
	STATUS		current
	DESCRIPTION "Rx Total Channels
			Oid=1.3.6.1.4.1.31968.3.1.4.1.5.2
			"
	::= { rxConfigItems 2 }

rxSmart OBJECT-TYPE
	SYNTAX		INTEGER {
		off(0),
		on(1)
	}
	MAX-ACCESS	read-write
	STATUS		current
	DESCRIPTION "Rx Smart Carrier, where:
			    0) 'Off'
			    1) 'On'
			Oid=1.3.6.1.4.1.31968.3.1.4.1.5.3
			"
	::= { rxConfigItems 3 }

rxMinDelay OBJECT-TYPE
	SYNTAX		Unsigned32
	UNITS		"0.1 ms"
	MAX-ACCESS	read-write
	STATUS		current
	DESCRIPTION "Rx Sat Echo Minimum Delay
			Oid=1.3.6.1.4.1.31968.3.1.4.1.5.4
			"
	::= { rxConfigItems 4 }

rxMaxDelay OBJECT-TYPE
	SYNTAX		Unsigned32
	UNITS		"0.1 ms"
	MAX-ACCESS	read-write
	STATUS		current
	DESCRIPTION "Rx Sat Echo Maximum Delay
			Oid=1.3.6.1.4.1.31968.3.1.4.1.5.5
			"
	::= { rxConfigItems 5 }

rxHoldDelay OBJECT-TYPE
	SYNTAX		Unsigned32
	UNITS		"0.1 s"
	MAX-ACCESS	read-write
	STATUS		current
	DESCRIPTION "Rx Sat Echo Delay Search Hold
			Oid=1.3.6.1.4.1.31968.3.1.4.1.5.6
			"
	::= { rxConfigItems 6 }

rxEchoLevelLimit OBJECT-TYPE
	SYNTAX		Unsigned32
	UNITS		"0.01 dB"
	MAX-ACCESS	read-write
	STATUS		current
	DESCRIPTION "Rx Echo Level Imbalance Limit
			Oid=1.3.6.1.4.1.31968.3.1.4.1.5.7
			"
	::= { rxConfigItems 7 }

rxEchoLevelAlarm OBJECT-TYPE
	SYNTAX		INTEGER {
		off(0),
		report(1),
		alarm(3),
		alarmAndRelayOutput(5)
	}
	MAX-ACCESS	read-write
	STATUS		current
	DESCRIPTION "Rx Echo Level Imbalance Alarm, where:
			    0) 'Off'
			    1) 'Report'
			    3) 'Alarm'
			    5) 'Alarm & Relay Output'
			Oid=1.3.6.1.4.1.31968.3.1.4.1.5.8
			"
	::= { rxConfigItems 8 }

rxEchoOffsetLimit OBJECT-TYPE
	SYNTAX		Unsigned32
	UNITS		"0.01%"
	MAX-ACCESS	read-write
	STATUS		current
	DESCRIPTION "Rx Echo Offset Imbalance Limit
			Oid=1.3.6.1.4.1.31968.3.1.4.1.5.9
			"
	::= { rxConfigItems 9 }

rxEchoOffsetAlarm OBJECT-TYPE
	SYNTAX		INTEGER {
		off(0),
		report(1),
		alarm(3),
		alarmAndRelayOutput(5)
	}
	MAX-ACCESS	read-write
	STATUS		current
	DESCRIPTION "Rx Echo Offset Imbalance Alarm, where:
			    0) 'Off'
			    1) 'Report'
			    3) 'Alarm'
			    5) 'Alarm & Relay Output'
			Oid=1.3.6.1.4.1.31968.3.1.4.1.5.10
			"
	::= { rxConfigItems 10 }

rxRemoteTxEsn0Mode OBJECT-TYPE
	SYNTAX		INTEGER {
		liveChannelsOnly(0),
		liveAndIdleChannels(1)
	}
	MAX-ACCESS	read-write
	STATUS		current
	DESCRIPTION "Rx Remote Tx Es/N0 Mode, where:
			    0) 'Live Channels Only'
			    1) 'Live & Idle Channels'
			Oid=1.3.6.1.4.1.31968.3.1.4.1.5.11
			"
	::= { rxConfigItems 11 }

rxLnbLo OBJECT-TYPE
	SYNTAX		DisplayString(SIZE(1..24))
	UNITS		"1 Hz"
	MAX-ACCESS	read-write
	STATUS		current
	DESCRIPTION "Rx LNB LO Frequency,
			    Text Number, Decimal, 0=Off
			Oid=1.3.6.1.4.1.31968.3.1.4.1.5.13
			"
	::= { rxConfigItems 13 }

rxLnbSide OBJECT-TYPE
	SYNTAX		INTEGER {
		low(0),
		high(1)
	}
	MAX-ACCESS	read-write
	STATUS		current
	DESCRIPTION "Rx LNB LO Side, where:
			    0) 'Low'
			    1) 'High'
			Oid=1.3.6.1.4.1.31968.3.1.4.1.5.14
			"
	::= { rxConfigItems 14 }

rxLnbRef OBJECT-TYPE
	SYNTAX		INTEGER {
		off(0),
		n10Mhz(1),
		n50Mhz(2)
	}
	MAX-ACCESS	read-write
	STATUS		current
	DESCRIPTION "Rx LNB Reference, where:
			    0) 'Off'
			    1) '10 MHz'
			    2) '50 MHz'
			Oid=1.3.6.1.4.1.31968.3.1.4.1.5.15
			"
	::= { rxConfigItems 15 }

rxLnbPower OBJECT-TYPE
	SYNTAX		INTEGER {
		off(0),
		p13V(1),
		p18V(2)
	}
	MAX-ACCESS	read-write
	STATUS		current
	DESCRIPTION "Rx LNB Power, where:
			    0) 'Off'
			    1) '+13 V'
			    2) '+18 V'
			Oid=1.3.6.1.4.1.31968.3.1.4.1.5.16
			"
	::= { rxConfigItems 16 }

rxLnbMin OBJECT-TYPE
	SYNTAX		Unsigned32
	UNITS		"1 ma"
	MAX-ACCESS	read-write
	STATUS		current
	DESCRIPTION "Rx LNB Minimum Current
			Oid=1.3.6.1.4.1.31968.3.1.4.1.5.17
			"
	::= { rxConfigItems 17 }

rxLnbMax OBJECT-TYPE
	SYNTAX		Unsigned32
	UNITS		"1 ma"
	MAX-ACCESS	read-write
	STATUS		current
	DESCRIPTION "Rx LNB Maximum Current
			Oid=1.3.6.1.4.1.31968.3.1.4.1.5.18
			"
	::= { rxConfigItems 18 }

rxLnbAlarm OBJECT-TYPE
	SYNTAX		INTEGER {
		off(0),
		report(1),
		alarm(3),
		alarmAndRelayOutput(5)
	}
	MAX-ACCESS	read-write
	STATUS		current
	DESCRIPTION "Rx LNB Power Alarm, where:
			    0) 'Off'
			    1) 'Report'
			    3) 'Alarm'
			    5) 'Alarm & Relay Output'
			Oid=1.3.6.1.4.1.31968.3.1.4.1.5.19
			"
	::= { rxConfigItems 19 }

rxLnbCenterFrequency OBJECT-TYPE
	SYNTAX		DisplayString(SIZE(1..24))
	UNITS		"1 Hz"
	MAX-ACCESS	read-write
	STATUS		current
	DESCRIPTION "Rx LNB Center Frequency,
			    Text Number, Decimal
			Oid=1.3.6.1.4.1.31968.3.1.4.1.5.20
			"
	::= { rxConfigItems 20 }

rxCenterFrequency OBJECT-TYPE
	SYNTAX		Unsigned32
	UNITS		"1 Hz"
	MAX-ACCESS	read-write
	STATUS		current
	DESCRIPTION "Rx Center Frequency
			Oid=1.3.6.1.4.1.31968.3.1.4.1.5.21
			"
	::= { rxConfigItems 21 }

rxGseDataProtocol OBJECT-TYPE
	SYNTAX		INTEGER {
		gseDvb(0),
		gseLowOverhead(1),
		gseCt(2),
		gseCt2(3),
		gseDvbM7(4)
	}
	MAX-ACCESS	read-write
	STATUS		current
	DESCRIPTION "Rx Protocol, where:
			    0) 'GSE DVB'
			    1) 'GSE Low Overhead'
			    2) 'GSE CT'
			    3) 'GSE CT2'
			    4) 'GSE DVB (M7)'
			Oid=1.3.6.1.4.1.31968.3.1.4.1.5.22
			"
	::= { rxConfigItems 22 }

rxHdlcDataProtocol OBJECT-TYPE
	SYNTAX		INTEGER {
		m500Hdlc(0),
		m7Hdlc(1),
		m7HdlcHoe(2)
	}
	MAX-ACCESS	read-write
	STATUS		current
	DESCRIPTION "Rx Protocol, where:
			    0) 'M500 HDLC'
			    1) 'M7 HDLC'
			    2) 'M7 HDLC HoE'
			Oid=1.3.6.1.4.1.31968.3.1.4.1.5.23
			"
	::= { rxConfigItems 23 }

rxDataIdle OBJECT-TYPE
	SYNTAX		INTEGER {
		off(0),
		on(1)
	}
	MAX-ACCESS	read-write
	STATUS		current
	DESCRIPTION "Rx Idle Packets, where:
			    0) 'Off'
			    1) 'On'
			Oid=1.3.6.1.4.1.31968.3.1.4.1.5.24
			"
	::= { rxConfigItems 24 }

rxDataMcc OBJECT-TYPE
	SYNTAX		INTEGER {
		off(0),
		on(1)
	}
	MAX-ACCESS	read-write
	STATUS		current
	DESCRIPTION "Rx MCC/ACM Packets, where:
			    0) 'Off'
			    1) 'On'
			Oid=1.3.6.1.4.1.31968.3.1.4.1.5.25
			"
	::= { rxConfigItems 25 }

rxLocalIpAddress OBJECT-TYPE
	SYNTAX		IpAddress
	MAX-ACCESS	read-write
	STATUS		current
	DESCRIPTION "Rx Local Tx IP Address
			Oid=1.3.6.1.4.1.31968.3.1.4.1.5.26
			"
	::= { rxConfigItems 26 }

rxDataHoeSmac OBJECT-TYPE
	SYNTAX		PhysAddress
	MAX-ACCESS	read-write
	STATUS		current
	DESCRIPTION "Rx HoE SMAC Address
			Oid=1.3.6.1.4.1.31968.3.1.4.1.5.27
			"
	::= { rxConfigItems 27 }

rxDataHoeDmac OBJECT-TYPE
	SYNTAX		PhysAddress
	MAX-ACCESS	read-write
	STATUS		current
	DESCRIPTION "Rx HoE DMAC Address
			Oid=1.3.6.1.4.1.31968.3.1.4.1.5.28
			"
	::= { rxConfigItems 28 }

rxMccMode OBJECT-TYPE
	SYNTAX		INTEGER {
		readOnly(0),
		fullAccess(1)
	}
	MAX-ACCESS	read-write
	STATUS		current
	DESCRIPTION "Rx MCC Mode, where:
			    0) 'Read Only'
			    1) 'Full Access'
			Oid=1.3.6.1.4.1.31968.3.1.4.1.5.29
			"
	::= { rxConfigItems 29 }

rxMccProtocol OBJECT-TYPE
	SYNTAX		INTEGER {
		m7BinaryPacket(0),
		m7xcBinaryPacket(1)
	}
	MAX-ACCESS	read-write
	STATUS		current
	DESCRIPTION "Rx MCC Protocol, where:
			    0) 'M7 Binary Packet'
			    1) 'M7XC Binary Packet'
			Oid=1.3.6.1.4.1.31968.3.1.4.1.5.30
			"
	::= { rxConfigItems 30 }

rxMccAddress OBJECT-TYPE
	SYNTAX		Unsigned32
	UNITS		"1"
	MAX-ACCESS	read-write
	STATUS		current
	DESCRIPTION "Rx MCC Address
			Oid=1.3.6.1.4.1.31968.3.1.4.1.5.31
			"
	::= { rxConfigItems 31 }

rxActivity OBJECT-TYPE
	SYNTAX		INTEGER {
		none(0),
		flashOnline(1)
	}
	MAX-ACCESS	read-write
	STATUS		current
	DESCRIPTION "Rx Activity, where:
			    0) 'None'
			    1) 'Flash Online'
			Oid=1.3.6.1.4.1.31968.3.1.4.1.5.32
			"
	::= { rxConfigItems 32 }

rxEchoLevelEvent OBJECT-TYPE
	SYNTAX		INTEGER {
		doNotLog(0),
		log(1),
		logAndSendAlert(2),
		logAndSendAlertNowNoDebounce(3)
	}
	MAX-ACCESS	read-write
	STATUS		current
	DESCRIPTION "Rx Low Echo Level Alarm Event, where:
			    0) 'Do Not Log'
			    1) 'Log'
			    2) 'Log & Send Alert'
			    3) 'Log & Send Alert Now (No Debounce)'
			Oid=1.3.6.1.4.1.31968.3.1.4.1.5.34
			"
	::= { rxConfigItems 34 }

rxEchoOffsetEvent OBJECT-TYPE
	SYNTAX		INTEGER {
		doNotLog(0),
		log(1),
		logAndSendAlert(2),
		logAndSendAlertNowNoDebounce(3)
	}
	MAX-ACCESS	read-write
	STATUS		current
	DESCRIPTION "Rx Echo Offset Alarm Event, where:
			    0) 'Do Not Log'
			    1) 'Log'
			    2) 'Log & Send Alert'
			    3) 'Log & Send Alert Now (No Debounce)'
			Oid=1.3.6.1.4.1.31968.3.1.4.1.5.35
			"
	::= { rxConfigItems 35 }

rxLnbEvent OBJECT-TYPE
	SYNTAX		INTEGER {
		doNotLog(0),
		log(1),
		logAndSendAlert(2),
		logAndSendAlertNowNoDebounce(3)
	}
	MAX-ACCESS	read-write
	STATUS		current
	DESCRIPTION "Rx LNB Power Alarm Event, where:
			    0) 'Do Not Log'
			    1) 'Log'
			    2) 'Log & Send Alert'
			    3) 'Log & Send Alert Now (No Debounce)'
			Oid=1.3.6.1.4.1.31968.3.1.4.1.5.36
			"
	::= { rxConfigItems 36 }

rxRfBandwidth OBJECT-TYPE
	SYNTAX		INTEGER {
		n12Mhz(0),
		n45Mhz(1),
		n18Mhz(2),
		n100Mhz(3)
	}
	MAX-ACCESS	read-write
	STATUS		current
	DESCRIPTION "Rx RF Input BW, where:
			    0) '1.2 MHz'
			    1) '4.5 MHz'
			    2) '18 MHz'
			    3) '100 MHz'
			Oid=1.3.6.1.4.1.31968.3.1.4.1.5.38
			"
	::= { rxConfigItems 38 }

rxAnalyzerLnbCenterFrequency OBJECT-TYPE
	SYNTAX		DisplayString(SIZE(1..24))
	UNITS		"1 Hz"
	MAX-ACCESS	read-write
	STATUS		current
	DESCRIPTION "Rx LNB Center Frequency,
			    Text Number, Decimal
			Oid=1.3.6.1.4.1.31968.3.1.4.1.5.39
			"
	::= { rxConfigItems 39 }

rxAnalyzerCenterFrequency OBJECT-TYPE
	SYNTAX		Unsigned32
	UNITS		"1 Hz"
	MAX-ACCESS	read-write
	STATUS		current
	DESCRIPTION "Rx Center Frequency
			Oid=1.3.6.1.4.1.31968.3.1.4.1.5.40
			"
	::= { rxConfigItems 40 }

rxAnalyzerSpanFrequency OBJECT-TYPE
	SYNTAX		Unsigned32
	UNITS		"1 Hz"
	MAX-ACCESS	read-write
	STATUS		current
	DESCRIPTION "Rx Span Frequency
			Oid=1.3.6.1.4.1.31968.3.1.4.1.5.41
			"
	::= { rxConfigItems 41 }

rxAnalyzerDisplay OBJECT-TYPE
	SYNTAX		INTEGER {
		normal(0),
		minHold(1),
		maxHold(2),
		minAndMaxHold(3)
	}
	MAX-ACCESS	read-write
	STATUS		current
	DESCRIPTION "Rx Display Mode, where:
			    0) 'Normal'
			    1) 'Min Hold'
			    2) 'Max Hold'
			    3) 'Min & Max Hold'
			Oid=1.3.6.1.4.1.31968.3.1.4.1.5.42
			"
	::= { rxConfigItems 42 }

rxAnalyzerLevel OBJECT-TYPE
	SYNTAX		Integer32
	UNITS		"0.01 dBm"
	MAX-ACCESS	read-write
	STATUS		current
	DESCRIPTION "Rx Maximum Level
			Oid=1.3.6.1.4.1.31968.3.1.4.1.5.43
			"
	::= { rxConfigItems 43 }

rxAnalyzerOffset OBJECT-TYPE
	SYNTAX		Integer32
	UNITS		"0.01 dB"
	MAX-ACCESS	read-write
	STATUS		current
	DESCRIPTION "Rx Offset Level
			Oid=1.3.6.1.4.1.31968.3.1.4.1.5.44
			"
	::= { rxConfigItems 44 }

rxAnalyzerScale OBJECT-TYPE
	SYNTAX		INTEGER {
		n1Db(0),
		n2Db(1),
		n5Db(2),
		n10Db(3)
	}
	MAX-ACCESS	read-write
	STATUS		current
	DESCRIPTION "Rx Display Scale, where:
			    0) '1 dB'
			    1) '2 dB'
			    2) '5 dB'
			    3) '10 dB'
			Oid=1.3.6.1.4.1.31968.3.1.4.1.5.45
			"
	::= { rxConfigItems 45 }

rxCalTask OBJECT-TYPE
	SYNTAX		INTEGER {
		idle(0),
		runIAndQAndLevelCal(1),
		runIAndQCal(2),
		runLevelCal(3)
	}
	MAX-ACCESS	read-write
	STATUS		current
	DESCRIPTION "Rx Calibration Task, where:
			    0) 'Idle'
			    1) 'Run I & Q And Level Cal'
			    2) 'Run I & Q Cal'
			    3) 'Run Level Cal'
			Oid=1.3.6.1.4.1.31968.3.1.4.1.5.46
			"
	::= { rxConfigItems 46 }

rxDataPortLinkRateAlarm OBJECT-TYPE
	SYNTAX		INTEGER {
		off(0),
		report(1),
		alarm(3),
		alarmAndRelayOutput(5)
	}
	MAX-ACCESS	read-write
	STATUS		current
	DESCRIPTION "Rx Data Port Link Rate Alarm, where:
			    0) 'Off'
			    1) 'Report'
			    3) 'Alarm'
			    5) 'Alarm & Relay Output'
			Oid=1.3.6.1.4.1.31968.3.1.4.1.5.49
			"
	::= { rxConfigItems 49 }

rxDataPortLinkRateEvent OBJECT-TYPE
	SYNTAX		INTEGER {
		doNotLog(0),
		log(1),
		logAndSendAlert(2),
		logAndSendAlertNowNoDebounce(3)
	}
	MAX-ACCESS	read-write
	STATUS		current
	DESCRIPTION "Rx Data Port Link Rate Alarm Event, where:
			    0) 'Do Not Log'
			    1) 'Log'
			    2) 'Log & Send Alert'
			    3) 'Log & Send Alert Now (No Debounce)'
			Oid=1.3.6.1.4.1.31968.3.1.4.1.5.50
			"
	::= { rxConfigItems 50 }

rxHdrFixedModcod OBJECT-TYPE
	SYNTAX		INTEGER {
		fr80t5x4L8(0),
		fr80t5x4L7(1),
		fr80t5x4L6(2),
		fr80t5x4L5(3),
		fr80t5x4L4(4),
		fr80t5x4L3(5),
		fr80t5x4L2(6),
		fr80t5x4L1(7),
		fr80t5x16L3(8),
		fr80t5x16L2(9),
		fr80t5x16L1(10),
		fr80t5x16R(11),
		fr80t5x16H1(12),
		fr80t5x16H2(13),
		fr80t5x16H3(14),
		fr80t5x16H4(15),
		fr80t5x16H5(16),
		fr80t5x16H6(17),
		fr80t5x32H1(18),
		fr80t5x32H2(19),
		fr80t5x32H3(20),
		fr80t5x32H4(21),
		fr80t5x32H5(22),
		fr80t5x32H6(23),
		fr80t5x64R(24),
		fr80t5x64H1(25),
		fr80t5x64H2(26),
		fr80t5x64H3(27),
		fr80t5x64H4(28),
		fr80t5x64H5(29),
		fr80t5x64H6(30)
	}
	MAX-ACCESS	read-write
	STATUS		current
	DESCRIPTION "Rx ModCod, where:
			    0) 'FR80T5X4-L8'
			    1) 'FR80T5X4-L7'
			    2) 'FR80T5X4-L6'
			    3) 'FR80T5X4-L5'
			    4) 'FR80T5X4-L4'
			    5) 'FR80T5X4-L3'
			    6) 'FR80T5X4-L2'
			    7) 'FR80T5X4-L1'
			    8) 'FR80T5X16-L3'
			    9) 'FR80T5X16-L2'
			    10) 'FR80T5X16-L1'
			    11) 'FR80T5X16-R'
			    12) 'FR80T5X16-H1'
			    13) 'FR80T5X16-H2'
			    14) 'FR80T5X16-H3'
			    15) 'FR80T5X16-H4'
			    16) 'FR80T5X16-H5'
			    17) 'FR80T5X16-H6'
			    18) 'FR80T5X32-H1'
			    19) 'FR80T5X32-H2'
			    20) 'FR80T5X32-H3'
			    21) 'FR80T5X32-H4'
			    22) 'FR80T5X32-H5'
			    23) 'FR80T5X32-H6'
			    24) 'FR80T5X64-R'
			    25) 'FR80T5X64-H1'
			    26) 'FR80T5X64-H2'
			    27) 'FR80T5X64-H3'
			    28) 'FR80T5X64-H4'
			    29) 'FR80T5X64-H5'
			    30) 'FR80T5X64-H6'
			Oid=1.3.6.1.4.1.31968.3.1.4.1.5.51
			"
	::= { rxConfigItems 51 }

rxHdrRotorThreshold OBJECT-TYPE
	SYNTAX		Integer32
	UNITS		"0.01 dB"
	MAX-ACCESS	read-write
	STATUS		current
	DESCRIPTION "Rx Rotor Threshold,
			    0=Off
			Oid=1.3.6.1.4.1.31968.3.1.4.1.5.52
			"
	::= { rxConfigItems 52 }

rxHdrRotorLead OBJECT-TYPE
	SYNTAX		Integer32
	UNITS		"1"
	MAX-ACCESS	read-write
	STATUS		current
	DESCRIPTION "Rx Rotor Lead
			Oid=1.3.6.1.4.1.31968.3.1.4.1.5.53
			"
	::= { rxConfigItems 53 }

rxHdrRotorLag OBJECT-TYPE
	SYNTAX		Integer32
	UNITS		"1"
	MAX-ACCESS	read-write
	STATUS		current
	DESCRIPTION "Rx Rotor Lag
			Oid=1.3.6.1.4.1.31968.3.1.4.1.5.54
			"
	::= { rxConfigItems 54 }

rxHdrSymbolRate OBJECT-TYPE
	SYNTAX		Unsigned32
	UNITS		"1 sps"
	MAX-ACCESS	read-write
	STATUS		current
	DESCRIPTION "Rx Symbol Rate
			Oid=1.3.6.1.4.1.31968.3.1.4.1.5.55
			"
	::= { rxConfigItems 55 }

rxRemoteMacAddress OBJECT-TYPE
	SYNTAX		PhysAddress
	MAX-ACCESS	read-write
	STATUS		current
	DESCRIPTION "Rx Tx Hub MAC Address
			Oid=1.3.6.1.4.1.31968.3.1.4.1.5.56
			"
	::= { rxConfigItems 56 }

rxAcmTxHubMsgAlarm OBJECT-TYPE
	SYNTAX		INTEGER {
		off(0),
		report(1),
		alarm(3),
		alarmAndRelayOutput(5)
	}
	MAX-ACCESS	read-write
	STATUS		current
	DESCRIPTION "Rx ACM Tx Hub Message Alarm - ACR Tx Hub Message Alarm, where:
			    0) 'Off'
			    1) 'Report'
			    3) 'Alarm'
			    5) 'Alarm & Relay Output'
			Oid=1.3.6.1.4.1.31968.3.1.4.1.5.57
			"
	::= { rxConfigItems 57 }

rxAcmTxHubMsgEvent OBJECT-TYPE
	SYNTAX		INTEGER {
		doNotLog(0),
		log(1),
		logAndSendAlert(2),
		logAndSendAlertNowNoDebounce(3)
	}
	MAX-ACCESS	read-write
	STATUS		current
	DESCRIPTION "Rx ACM Tx Hub Message Event - ACR Tx Hub Message Event, where:
			    0) 'Do Not Log'
			    1) 'Log'
			    2) 'Log & Send Alert'
			    3) 'Log & Send Alert Now (No Debounce)'
			Oid=1.3.6.1.4.1.31968.3.1.4.1.5.58
			"
	::= { rxConfigItems 58 }

rxConfigTable OBJECT-TYPE
	SYNTAX		SEQUENCE OF RxConfigEntry
	MAX-ACCESS	not-accessible
	STATUS		current
	DESCRIPTION "Rx Config Channel Table
			Oid=1.3.6.1.4.1.31968.3.1.4.1.6
			"
	::= { m7xcModemObjs 6 }

rxConfigEntry OBJECT-TYPE
	SYNTAX		RxConfigEntry
	MAX-ACCESS	not-accessible
	STATUS		current
	DESCRIPTION "Rx Config Channel Entry
			Oid=1.3.6.1.4.1.31968.3.1.4.1.6.1
			"
	INDEX {
		rxConfigIndex
	}
	::= { rxConfigTable 1 }

RxConfigEntry ::=
	SEQUENCE {
		rxConfigIndex           Unsigned32,
		rxLockAlarm             INTEGER,
		rxEsn0Margin            Integer32,
		rxEsn0Alarm             INTEGER,
		rxLevelLimit            Integer32,
		rxLevelAlarm            INTEGER,
		rxAcmLowEsn0Alarm       INTEGER,
		rxAcmLowEsn0Limit       Integer32,
		rxFrameStatsReset       INTEGER,
		rxTrafficStatsReset     INTEGER,
		rxLnbFrequency          DisplayString,
		rxFrequency             Unsigned32,
		rxRollOff               INTEGER,
		rxRemotePath            INTEGER,
		rxRemoteMccAddress      Unsigned32,
		rxSymbolRate            Unsigned32,
		rxDvbDescrambler        Unsigned32,
		rxLdpcBlock             INTEGER,
		rxLdpcDescrambler       INTEGER,
		rxFromTxQueue           Unsigned32,
		rxTransecOperation      INTEGER,
		rxDataInactive          Unsigned32,
		rxDataAlarm             INTEGER,
		rxLockEvent             INTEGER,
		rxEsn0Event             INTEGER,
		rxLevelEvent            INTEGER,
		rxAcmEvent              INTEGER,
		rxAcmLowEsn0Event       INTEGER,
		rxDataEvent             INTEGER,
		rxChannel               INTEGER,
		rxTransecKeySize        INTEGER,
		rxTransecKey            DisplayString,
		rxTransecKeyHash        DisplayString,
		rxTransecAlarm          INTEGER,
		rxTransecEvent          INTEGER,
		rxMuteTxOutputDelay     Unsigned32,
		rxModcodEvent           INTEGER,
		rxDsssChipRate          Unsigned32,
		rxDsssSpreadFactor      Unsigned32,
		rxDsssCodeLength        INTEGER,
		rxDsssCode              Unsigned32,
		rxAcrLowSnrLimit        Integer32,
		rxMinAcquisitionRange   Integer32,
		rxRemoteChannelId       Integer32
	}

rxConfigIndex OBJECT-TYPE
	SYNTAX		Unsigned32(1..16)
	MAX-ACCESS	not-accessible
	STATUS		current
	DESCRIPTION "Rx Config Channel Index
			Oid=1.3.6.1.4.1.31968.3.1.4.1.6.1.1
			"
	::= { rxConfigEntry 1 }

rxLockAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Rx Lock Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.6.1.2
			"
	::= { rxConfigEntry 2 }

rxEsn0Margin OBJECT-TYPE
	SYNTAX		Integer32
	UNITS		"0.01 dB"
	MAX-ACCESS	read-write
	STATUS		current
	DESCRIPTION "Rx Low Es/N0 Margin - Low SNR Margin
			Oid=1.3.6.1.4.1.31968.3.1.4.1.6.1.3
			"
	::= { rxConfigEntry 3 }

rxEsn0Alarm OBJECT-TYPE
	SYNTAX		INTEGER {
		off(0),
		report(1),
		alarm(3),
		alarmAndRelayOutput(5)
	}
	MAX-ACCESS	read-write
	STATUS		current
	DESCRIPTION "Rx Low Es/N0 Alarm - Low SNR Alarm, where:
			    0) 'Off'
			    1) 'Report'
			    3) 'Alarm'
			    5) 'Alarm & Relay Output'
			Oid=1.3.6.1.4.1.31968.3.1.4.1.6.1.4
			"
	::= { rxConfigEntry 4 }

rxLevelLimit OBJECT-TYPE
	SYNTAX		Integer32
	UNITS		"0.01 dBm"
	MAX-ACCESS	read-write
	STATUS		current
	DESCRIPTION "Rx Low Level Limit
			Oid=1.3.6.1.4.1.31968.3.1.4.1.6.1.5
			"
	::= { rxConfigEntry 5 }

rxLevelAlarm OBJECT-TYPE
	SYNTAX		INTEGER {
		off(0),
		report(1),
		alarm(3),
		alarmAndRelayOutput(5)
	}
	MAX-ACCESS	read-write
	STATUS		current
	DESCRIPTION "Rx Low Level Alarm, where:
			    0) 'Off'
			    1) 'Report'
			    3) 'Alarm'
			    5) 'Alarm & Relay Output'
			Oid=1.3.6.1.4.1.31968.3.1.4.1.6.1.6
			"
	::= { rxConfigEntry 6 }

rxAcmLowEsn0Alarm OBJECT-TYPE
	SYNTAX		INTEGER {
		off(0),
		report(1),
		alarm(3),
		alarmAndRelayOutput(5)
	}
	MAX-ACCESS	read-write
	STATUS		current
	DESCRIPTION "Rx ACM Low Es/N0 Alarm - ACR Low SNR Alarm, where:
			    0) 'Off'
			    1) 'Report'
			    3) 'Alarm'
			    5) 'Alarm & Relay Output'
			Oid=1.3.6.1.4.1.31968.3.1.4.1.6.1.7
			"
	::= { rxConfigEntry 7 }

rxAcmLowEsn0Limit OBJECT-TYPE
	SYNTAX		Integer32
	UNITS		"0.01 dB"
	MAX-ACCESS	read-write
	STATUS		current
	DESCRIPTION "Rx ACM Low Es/N0 Limit
			Oid=1.3.6.1.4.1.31968.3.1.4.1.6.1.8
			"
	::= { rxConfigEntry 8 }

rxFrameStatsReset OBJECT-TYPE
	SYNTAX		INTEGER {
		statsRunning(0),
		resetSelfClearing(1)
	}
	MAX-ACCESS	read-write
	STATUS		current
	DESCRIPTION "Rx Frame Statistics Reset, where:
			    0) 'Stats Running...'
			    1) 'Reset, Self Clearing'
			Oid=1.3.6.1.4.1.31968.3.1.4.1.6.1.9
			"
	::= { rxConfigEntry 9 }

rxTrafficStatsReset OBJECT-TYPE
	SYNTAX		INTEGER {
		statsRunning(0),
		resetSelfClearing(1)
	}
	MAX-ACCESS	read-write
	STATUS		current
	DESCRIPTION "Rx Traffic Statistics Reset, where:
			    0) 'Stats Running...'
			    1) 'Reset - Self Clearing'
			Oid=1.3.6.1.4.1.31968.3.1.4.1.6.1.10
			"
	::= { rxConfigEntry 10 }

rxLnbFrequency OBJECT-TYPE
	SYNTAX		DisplayString(SIZE(1..24))
	UNITS		"1 Hz"
	MAX-ACCESS	read-write
	STATUS		current
	DESCRIPTION "Rx LNB Carrier Frequency,
			    Text Number, Decimal
			Oid=1.3.6.1.4.1.31968.3.1.4.1.6.1.11
			"
	::= { rxConfigEntry 11 }

rxFrequency OBJECT-TYPE
	SYNTAX		Unsigned32
	UNITS		"1 Hz"
	MAX-ACCESS	read-write
	STATUS		current
	DESCRIPTION "Rx Carrier Frequency
			Oid=1.3.6.1.4.1.31968.3.1.4.1.6.1.12
			"
	::= { rxConfigEntry 12 }

rxRollOff OBJECT-TYPE
	SYNTAX		INTEGER {
		n35Percent(0),
		n30Percent(1),
		n25Percent(2),
		n20Percent(3),
		n15Percent(4),
		n10Percent(5),
		n5Percent(6),
		n2Percent(7),
		n40Percent(8),
		n45Percent(9)
	}
	MAX-ACCESS	read-write
	STATUS		current
	DESCRIPTION "Rx Roll-Off, where:
			    0) '35%'
			    1) '30%'
			    2) '25%'
			    3) '20%'
			    4) '15%'
			    5) '10%'
			    6) '5%'
			    7) '2%'
			    8) '40%'
			    9) '45%'
			Oid=1.3.6.1.4.1.31968.3.1.4.1.6.1.13
			"
	::= { rxConfigEntry 13 }

rxRemotePath OBJECT-TYPE
	SYNTAX		INTEGER {
		off(0),
		localOneChannelOnly(1),
		outMccPort(2),
		outDataPort(3)
	}
	MAX-ACCESS	read-write
	STATUS		current
	DESCRIPTION "Rx Remote Tx Path, where:
			    0) 'Off'
			    1) 'Local (One Channel Only)'
			    2) 'Out MCC Port'
			    3) 'Out Data Port'
			Oid=1.3.6.1.4.1.31968.3.1.4.1.6.1.14
			"
	::= { rxConfigEntry 14 }

rxRemoteMccAddress OBJECT-TYPE
	SYNTAX		Unsigned32
	UNITS		"1"
	MAX-ACCESS	read-write
	STATUS		current
	DESCRIPTION "Rx Remote Tx MCC Address,
			    255=Global
			Oid=1.3.6.1.4.1.31968.3.1.4.1.6.1.15
			"
	::= { rxConfigEntry 15 }

rxSymbolRate OBJECT-TYPE
	SYNTAX		Unsigned32
	UNITS		"1 sps"
	MAX-ACCESS	read-write
	STATUS		current
	DESCRIPTION "Rx Symbol Rate
			Oid=1.3.6.1.4.1.31968.3.1.4.1.6.1.16
			"
	::= { rxConfigEntry 16 }

rxDvbDescrambler OBJECT-TYPE
	SYNTAX		Unsigned32
	UNITS		"1"
	MAX-ACCESS	read-write
	STATUS		current
	DESCRIPTION "Rx PLS Descrambler Sequence
			Oid=1.3.6.1.4.1.31968.3.1.4.1.6.1.17
			"
	::= { rxConfigEntry 17 }

rxLdpcBlock OBJECT-TYPE
	SYNTAX		INTEGER {
		n2k(0),
		n4k(1),
		n8k(2),
		n16k(3)
	}
	MAX-ACCESS	read-write
	STATUS		current
	DESCRIPTION "Rx Block Size, where:
			    0) '2k'
			    1) '4k'
			    2) '8k'
			    3) '16k'
			Oid=1.3.6.1.4.1.31968.3.1.4.1.6.1.18
			"
	::= { rxConfigEntry 18 }

rxLdpcDescrambler OBJECT-TYPE
	SYNTAX		INTEGER {
		off(0),
		asynchronous(1),
		fecFrameSynchronous(2)
	}
	MAX-ACCESS	read-write
	STATUS		current
	DESCRIPTION "Rx Scrambler, where:
			    0) 'Off'
			    1) 'Asynchronous'
			    2) 'FEC Frame Synchronous'
			Oid=1.3.6.1.4.1.31968.3.1.4.1.6.1.19
			"
	::= { rxConfigEntry 19 }

rxFromTxQueue OBJECT-TYPE
	SYNTAX		Unsigned32
	UNITS		"1"
	MAX-ACCESS	read-write
	STATUS		current
	DESCRIPTION "Rx Receive From Tx Queue
			Oid=1.3.6.1.4.1.31968.3.1.4.1.6.1.20
			"
	::= { rxConfigEntry 20 }

rxTransecOperation OBJECT-TYPE
	SYNTAX		INTEGER {
		decryptionOff(0),
		decryptionOn(1),
		zeroizeRxKey(10),
		zeroizeAllRxKeys(11)
	}
	MAX-ACCESS	read-write
	STATUS		current
	DESCRIPTION "Rx Operation, where:
			    0) 'Decryption Off'
			    1) 'Decryption On'
			    10) 'Zeroize Rx Key'
			    11) 'Zeroize All Rx Keys'
			Oid=1.3.6.1.4.1.31968.3.1.4.1.6.1.21
			"
	::= { rxConfigEntry 21 }

rxDataInactive OBJECT-TYPE
	SYNTAX		Unsigned32
	UNITS		"s"
	MAX-ACCESS	read-write
	STATUS		current
	DESCRIPTION "Rx Data Inactive Time
			Oid=1.3.6.1.4.1.31968.3.1.4.1.6.1.22
			"
	::= { rxConfigEntry 22 }

rxDataAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Rx Data Inactive Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.6.1.23
			"
	::= { rxConfigEntry 23 }

rxLockEvent OBJECT-TYPE
	SYNTAX		INTEGER {
		doNotLog(0),
		log(1),
		logAndSendAlert(2),
		logAndSendAlertNowNoDebounce(3)
	}
	MAX-ACCESS	read-write
	STATUS		current
	DESCRIPTION "Rx Lock Event, where:
			    0) 'Do Not Log'
			    1) 'Log'
			    2) 'Log & Send Alert'
			    3) 'Log & Send Alert Now (No Debounce)'
			Oid=1.3.6.1.4.1.31968.3.1.4.1.6.1.24
			"
	::= { rxConfigEntry 24 }

rxEsn0Event OBJECT-TYPE
	SYNTAX		INTEGER {
		doNotLog(0),
		log(1),
		logAndSendAlert(2),
		logAndSendAlertNowNoDebounce(3)
	}
	MAX-ACCESS	read-write
	STATUS		current
	DESCRIPTION "Rx Low Es/N0 Alarm Event - Low SNR Alarm Event, where:
			    0) 'Do Not Log'
			    1) 'Log'
			    2) 'Log & Send Alert'
			    3) 'Log & Send Alert Now (No Debounce)'
			Oid=1.3.6.1.4.1.31968.3.1.4.1.6.1.25
			"
	::= { rxConfigEntry 25 }

rxLevelEvent OBJECT-TYPE
	SYNTAX		INTEGER {
		doNotLog(0),
		log(1),
		logAndSendAlert(2),
		logAndSendAlertNowNoDebounce(3)
	}
	MAX-ACCESS	read-write
	STATUS		current
	DESCRIPTION "Rx Low Level Alarm Event, where:
			    0) 'Do Not Log'
			    1) 'Log'
			    2) 'Log & Send Alert'
			    3) 'Log & Send Alert Now (No Debounce)'
			Oid=1.3.6.1.4.1.31968.3.1.4.1.6.1.26
			"
	::= { rxConfigEntry 26 }

rxAcmEvent OBJECT-TYPE
	SYNTAX		INTEGER {
		doNotLog(0),
		log(1),
		logAndSendAlert(2),
		logAndSendAlertNowNoDebounce(3)
	}
	MAX-ACCESS	read-write
	STATUS		current
	DESCRIPTION "Rx ACM Alarm Event - ACR Alarm Event, where:
			    0) 'Do Not Log'
			    1) 'Log'
			    2) 'Log & Send Alert'
			    3) 'Log & Send Alert Now (No Debounce)'
			Oid=1.3.6.1.4.1.31968.3.1.4.1.6.1.27
			"
	::= { rxConfigEntry 27 }

rxAcmLowEsn0Event OBJECT-TYPE
	SYNTAX		INTEGER {
		doNotLog(0),
		log(1),
		logAndSendAlert(2),
		logAndSendAlertNowNoDebounce(3)
	}
	MAX-ACCESS	read-write
	STATUS		current
	DESCRIPTION "Rx ACM Low Es/N0 Alarm Event - ACR Low SNR Alarm Event, where:
			    0) 'Do Not Log'
			    1) 'Log'
			    2) 'Log & Send Alert'
			    3) 'Log & Send Alert Now (No Debounce)'
			Oid=1.3.6.1.4.1.31968.3.1.4.1.6.1.28
			"
	::= { rxConfigEntry 28 }

rxDataEvent OBJECT-TYPE
	SYNTAX		INTEGER {
		doNotLog(0),
		log(1),
		logAndSendAlert(2),
		logAndSendAlertNowNoDebounce(3)
	}
	MAX-ACCESS	read-write
	STATUS		current
	DESCRIPTION "Rx Data Inactivity Alarm Event, where:
			    0) 'Do Not Log'
			    1) 'Log'
			    2) 'Log & Send Alert'
			    3) 'Log & Send Alert Now (No Debounce)'
			Oid=1.3.6.1.4.1.31968.3.1.4.1.6.1.29
			"
	::= { rxConfigEntry 29 }

rxChannel OBJECT-TYPE
	SYNTAX		INTEGER {
		off(0),
		on(1)
	}
	MAX-ACCESS	read-write
	STATUS		current
	DESCRIPTION "Rx Channel, where:
			    0) 'Off'
			    1) 'On'
			Oid=1.3.6.1.4.1.31968.3.1.4.1.6.1.30
			"
	::= { rxConfigEntry 30 }

rxTransecKeySize OBJECT-TYPE
	SYNTAX		INTEGER {
		aes128(0),
		aes192(1),
		aes256(2)
	}
	MAX-ACCESS	read-write
	STATUS		current
	DESCRIPTION "Rx Key Size, where:
			    0) 'AES-128'
			    1) 'AES-192'
			    2) 'AES-256'
			Oid=1.3.6.1.4.1.31968.3.1.4.1.6.1.31
			"
	::= { rxConfigEntry 31 }

rxTransecKey OBJECT-TYPE
	SYNTAX		DisplayString(SIZE(0..64))
	MAX-ACCESS	read-write
	STATUS		current
	DESCRIPTION "Rx Key
			Oid=1.3.6.1.4.1.31968.3.1.4.1.6.1.32
			"
	::= { rxConfigEntry 32 }

rxTransecKeyHash OBJECT-TYPE
	SYNTAX		DisplayString(SIZE(0..64))
	MAX-ACCESS	read-only
	STATUS		current
	DESCRIPTION "Rx Key Hash (SHA3-256)
			Oid=1.3.6.1.4.1.31968.3.1.4.1.6.1.33
			"
	::= { rxConfigEntry 33 }

rxTransecAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Rx TRANSEC Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.6.1.34
			"
	::= { rxConfigEntry 34 }

rxTransecEvent OBJECT-TYPE
	SYNTAX		INTEGER {
		doNotLog(0),
		log(1),
		logAndSendAlert(2),
		logAndSendAlertNowNoDebounce(3)
	}
	MAX-ACCESS	read-write
	STATUS		current
	DESCRIPTION "Rx TRANSEC Event, where:
			    0) 'Do Not Log'
			    1) 'Log'
			    2) 'Log & Send Alert'
			    3) 'Log & Send Alert Now (No Debounce)'
			Oid=1.3.6.1.4.1.31968.3.1.4.1.6.1.35
			"
	::= { rxConfigEntry 35 }

rxMuteTxOutputDelay OBJECT-TYPE
	SYNTAX		Unsigned32
	UNITS		"s"
	MAX-ACCESS	read-write
	STATUS		current
	DESCRIPTION "Rx Mute Tx Output Delay
			Oid=1.3.6.1.4.1.31968.3.1.4.1.6.1.36
			"
	::= { rxConfigEntry 36 }

rxModcodEvent OBJECT-TYPE
	SYNTAX		INTEGER {
		doNotLog(0),
		log(1),
		logAndSendAlert(2),
		logAndSendAlertNowNoDebounce(3)
	}
	MAX-ACCESS	read-write
	STATUS		current
	DESCRIPTION "Rx ModCod Event, where:
			    0) 'Do Not Log'
			    1) 'Log'
			    2) 'Log & Send Alert'
			    3) 'Log & Send Alert Now (No Debounce)'
			Oid=1.3.6.1.4.1.31968.3.1.4.1.6.1.37
			"
	::= { rxConfigEntry 37 }

rxDsssChipRate OBJECT-TYPE
	SYNTAX		Unsigned32
	MAX-ACCESS	read-write
	STATUS		current
	DESCRIPTION "Rx DSSS Chip Rate
			Oid=1.3.6.1.4.1.31968.3.1.4.1.6.1.38
			"
	::= { rxConfigEntry 38 }

rxDsssSpreadFactor OBJECT-TYPE
	SYNTAX		Unsigned32
	UNITS		"1"
	MAX-ACCESS	read-write
	STATUS		current
	DESCRIPTION "Rx DSSS Spread Factor
			Oid=1.3.6.1.4.1.31968.3.1.4.1.6.1.39
			"
	::= { rxConfigEntry 39 }

rxDsssCodeLength OBJECT-TYPE
	SYNTAX		INTEGER {
		n511(0),
		n4095SlowAcquisition(1)
	}
	MAX-ACCESS	read-write
	STATUS		current
	DESCRIPTION "Rx DSSS Code Sequence Length, where:
			    0) '511'
			    1) '4095 (Slow Acquisition)'
			Oid=1.3.6.1.4.1.31968.3.1.4.1.6.1.40
			"
	::= { rxConfigEntry 40 }

rxDsssCode OBJECT-TYPE
	SYNTAX		Unsigned32
	UNITS		"1"
	MAX-ACCESS	read-write
	STATUS		current
	DESCRIPTION "Rx DSSS Code Index
			Oid=1.3.6.1.4.1.31968.3.1.4.1.6.1.41
			"
	::= { rxConfigEntry 41 }

rxAcrLowSnrLimit OBJECT-TYPE
	SYNTAX		Integer32
	UNITS		"0.01 dB"
	MAX-ACCESS	read-write
	STATUS		current
	DESCRIPTION "Rx ACR Low SNR Limit
			Oid=1.3.6.1.4.1.31968.3.1.4.1.6.1.42
			"
	::= { rxConfigEntry 42 }

rxMinAcquisitionRange OBJECT-TYPE
	SYNTAX		Integer32
	UNITS		"1 Hz"
	MAX-ACCESS	read-write
	STATUS		current
	DESCRIPTION "Rx Minimum +/-Acquisition Range
			Oid=1.3.6.1.4.1.31968.3.1.4.1.6.1.43
			"
	::= { rxConfigEntry 43 }

rxRemoteChannelId OBJECT-TYPE
	SYNTAX		Integer32
	UNITS		"1"
	MAX-ACCESS	read-write
	STATUS		current
	DESCRIPTION "Rx Tx Hub Channel ID
			Oid=1.3.6.1.4.1.31968.3.1.4.1.6.1.44
			"
	::= { rxConfigEntry 44 }

txStatus OBJECT-TYPE
	SYNTAX		INTEGER {
		sendingOk(0),
		sendingOcxoWarming(1),
		sendingDataUpDownPending(2),
		sendingAcmLowModcodAlarm(3),
		sendingAupcLimitAlarm(4),
		sendingRemoteChanAlarm(5),
		sendingRefAlarm(6),
		sendingDataInactivityAlarm(7),
		sendingDataPortAlarm(8),
		sendingTestActive(9),
		offlineOk(10),
		offlineDataUpDownPending(11),
		offlineAcmLowModcodAlarm(12),
		offlineAupcLimitAlarm(13),
		offlineRemoteChanAlarm(14),
		offlineRefAlarm(15),
		offlineDataInactivityAlarm(16),
		offlineDataPortAlarm(17),
		offlineTestActive(18),
		standbyRxUnlocked(19),
		txMutedRxUnlocked(20),
		standbyMgmtPortAlarm(21),
		txMutedMgmtPortAlarm(22),
		standbyDataInactivityAlarm(23),
		txMutedDataInactivityAlarm(24),
		standbyDataPortAlarm(25),
		txMutedDataPortAlarm(26),
		standbyMonitorAlarm(27),
		txMutedMonitorAlarm(28),
		txMutedRefAlarm(29),
		txMutedOcxoWarming(30),
		txOutputOff(31),
		txOff(32),
		hardwareAlarm(33),
		systemAlarm(34),
		invalidKey(35),
		loadFailed(36),
		overTemperature(37),
		overTemperatureShutdown(38),
		txMutedTransecAlarm(39),
		sendingTxTransecAlarm(40)
	}
	MAX-ACCESS	read-only
	STATUS		current
	DESCRIPTION "Tx Status, where:
			    0) 'Sending, Ok'
			    1) 'Sending, OCXO Warming...'
			    2) 'Sending, Data Up/Down Pending'
			    3) 'Sending, ACM LOW MODCOD ALARM'
			    4) 'Sending, AUPC LIMIT ALARM'
			    5) 'Sending, REMOTE CHAN ALARM'
			    6) 'Sending, REF ALARM'
			    7) 'Sending, DATA INACTIVITY ALARM'
			    8) 'Sending, DATA PORT ALARM'
			    9) 'Sending, TEST ACTIVE'
			    10) 'Offline, Ok'
			    11) 'Offline, Data Up/Down Pending'
			    12) 'Offline, ACM LOW MODCOD ALARM'
			    13) 'Offline, AUPC LIMIT ALARM'
			    14) 'Offline, REMOTE CHAN ALARM'
			    15) 'Offline, REF ALARM'
			    16) 'Offline, DATA INACTIVITY ALARM'
			    17) 'Offline, DATA PORT ALARM'
			    18) 'Offline, TEST ACTIVE'
			    19) 'Standby, Rx Unlocked'
			    20) 'Tx MUTED, Rx UNLOCKED'
			    21) 'Standby, Mgmt Port Alarm'
			    22) 'Tx MUTED, Mgmt PORT ALARM'
			    23) 'Standby, Data Inactivity Alarm'
			    24) 'Tx MUTED, DATA INACTIVITY ALARM'
			    25) 'Standby, Data Port Alarm'
			    26) 'Tx MUTED, DATA PORT ALARM'
			    27) 'Standby, Monitor Alarm'
			    28) 'Tx MUTED, MONITOR ALARM'
			    29) 'Tx MUTED, REF ALARM'
			    30) 'Tx MUTED, OCXO WARMING...'
			    31) 'Tx OUTPUT OFF'
			    32) 'Tx Off'
			    33) 'HARDWARE ALARM'
			    34) 'SYSTEM ALARM'
			    35) 'INVALID KEY'
			    36) 'LOAD FAILED'
			    37) 'OVER TEMPERATURE'
			    38) 'OVER TEMPERATURE SHUTDOWN'
			    39) 'Tx MUTED, TRANSEC ALARM'
			    40) 'Sending, Tx TRANSEC ALARM'
			Oid=1.3.6.1.4.1.31968.3.1.4.1.7.1
			"
	::= { txStatusItems 1 }

txBinaryStatus OBJECT-TYPE
	SYNTAX		BITS {
		outputOn1(0),
		outputOn2(1),
		outputOn3(2),
		outputOn4(3),
		outputOn5(4),
		outputOn6(5),
		outputOn7(6),
		outputOn8(7),
		outputOn9(8),
		outputOn10(9),
		outputOn11(10),
		outputOn12(11),
		outputOn13(12),
		outputOn14(13),
		outputOn15(14),
		outputOn16(15),
		dataUp1(16),
		dataUp2(17),
		dataUp3(18),
		dataUp4(19),
		dataUp5(20),
		dataUp6(21),
		dataUp7(22),
		dataUp8(23),
		dataUp9(24),
		dataUp10(25),
		dataUp11(26),
		dataUp12(27),
		dataUp13(28),
		dataUp14(29),
		dataUp15(30),
		dataUp16(31),
		pending1(32),
		pending2(33),
		pending3(34),
		pending4(35),
		pending5(36),
		pending6(37),
		pending7(38),
		pending8(39),
		pending9(40),
		pending10(41),
		pending11(42),
		pending12(43),
		pending13(44),
		pending14(45),
		pending15(46),
		pending16(47),
		almData(48),
		almRef(49),
		almLoad(50),
		almKey(51),
		almTemp(52),
		almVint(53),
		almVaux(54),
		almClock(55),
		alm100Mhz(56),
		alm122Mhz(57),
		almLo(58),
		almEncoder(59),
		almLevel(60),
		almCxr(61),
		almMemory(62),
		almRfTemp(63),
		almTempShutdown(64),
		trialActive(65),
		almTransec(66),
		testActive(67)
	}
	MAX-ACCESS	read-only
	STATUS		current
	DESCRIPTION "Tx Binary Status, where:
			    0) 'Output On 1'
			    1) 'Output On 2'
			    2) 'Output On 3'
			    3) 'Output On 4'
			    4) 'Output On 5'
			    5) 'Output On 6'
			    6) 'Output On 7'
			    7) 'Output On 8'
			    8) 'Output On 9'
			    9) 'Output On 10'
			    10) 'Output On 11'
			    11) 'Output On 12'
			    12) 'Output On 13'
			    13) 'Output On 14'
			    14) 'Output On 15'
			    15) 'Output On 16'
			    16) 'Data Up 1'
			    17) 'Data Up 2'
			    18) 'Data Up 3'
			    19) 'Data Up 4'
			    20) 'Data Up 5'
			    21) 'Data Up 6'
			    22) 'Data Up 7'
			    23) 'Data Up 8'
			    24) 'Data Up 9'
			    25) 'Data Up 10'
			    26) 'Data Up 11'
			    27) 'Data Up 12'
			    28) 'Data Up 13'
			    29) 'Data Up 14'
			    30) 'Data Up 15'
			    31) 'Data Up 16'
			    32) 'Pending 1'
			    33) 'Pending 2'
			    34) 'Pending 3'
			    35) 'Pending 4'
			    36) 'Pending 5'
			    37) 'Pending 6'
			    38) 'Pending 7'
			    39) 'Pending 8'
			    40) 'Pending 9'
			    41) 'Pending 10'
			    42) 'Pending 11'
			    43) 'Pending 12'
			    44) 'Pending 13'
			    45) 'Pending 14'
			    46) 'Pending 15'
			    47) 'Pending 16'
			    48) 'Alm Data'
			    49) 'Alm Ref'
			    50) 'Alm Load'
			    51) 'Alm Key'
			    52) 'Alm Temp'
			    53) 'Alm VInt'
			    54) 'Alm VAux'
			    55) 'Alm Clock'
			    56) 'Alm 100 MHz'
			    57) 'Alm 122 MHz'
			    58) 'Alm LO'
			    59) 'Alm Encoder'
			    60) 'Alm Level'
			    61) 'Alm CXR'
			    62) 'Alm Memory'
			    63) 'Alm RF Temp'
			    64) 'Alm Temp Shutdown'
			    65) 'Trial Active'
			    66) 'Alm Transec'
			    67) 'Test Active'
			Oid=1.3.6.1.4.1.31968.3.1.4.1.7.2
			"
	::= { txStatusItems 2 }

txDvbModcod OBJECT-TYPE
	SYNTAX		INTEGER {
		qpsk1x4Normal(0),
		qpsk1x4NormalWithPilot(1),
		qpsk13x45Normal(2),
		qpsk13x45NormalWithPilot(3),
		qpsk1x3Normal(4),
		qpsk1x3NormalWithPilot(5),
		qpsk2x5Normal(6),
		qpsk2x5NormalWithPilot(7),
		qpsk9x20Normal(8),
		qpsk9x20NormalWithPilot(9),
		qpsk1x2Normal(10),
		qpsk1x2NormalWithPilot(11),
		qpsk11x20Normal(12),
		qpsk11x20NormalWithPilot(13),
		qpsk3x5Normal(14),
		qpsk3x5NormalWithPilot(15),
		qpsk2x3Normal(16),
		qpsk2x3NormalWithPilot(17),
		qpsk3x4Normal(18),
		qpsk3x4NormalWithPilot(19),
		qpsk4x5Normal(20),
		qpsk4x5NormalWithPilot(21),
		qpsk5x6Normal(22),
		qpsk5x6NormalWithPilot(23),
		qpsk8x9Normal(24),
		qpsk8x9NormalWithPilot(25),
		qpsk9x10Normal(26),
		qpsk9x10NormalWithPilot(27),
		n8apsk5x9LNormal(28),
		n8apsk5x9LNormalWithPilot(29),
		n8apsk26x45LNormal(30),
		n8apsk26x45LNormalWithPilot(31),
		n8psk3x5NormalWithPilot(32),
		n8psk23x36Normal(33),
		n8psk23x36NormalWithPilot(34),
		n8psk2x3NormalWithPilot(35),
		n8psk25x36Normal(36),
		n8psk25x36NormalWithPilot(37),
		n8psk13x18Normal(38),
		n8psk13x18NormalWithPilot(39),
		n8psk3x4Normal(40),
		n8psk3x4NormalWithPilot(41),
		n8psk5x6Normal(42),
		n8psk5x6NormalWithPilot(43),
		n8psk8x9Normal(44),
		n8psk8x9NormalWithPilot(45),
		n8psk9x10Normal(46),
		n8psk9x10NormalWithPilot(47),
		n16apsk1x2LNormal(48),
		n16apsk1x2LNormalWithPilot(49),
		n16apsk8x15LNormal(50),
		n16apsk8x15LNormalWithPilot(51),
		n16apsk5x9LNormal(52),
		n16apsk5x9LNormalWithPilot(53),
		n16apsk26x45Normal(54),
		n16apsk26x45NormalWithPilot(55),
		n16apsk3x5Normal(56),
		n16apsk3x5NormalWithPilot(57),
		n16apsk3x5LNormal(58),
		n16apsk3x5LNormalWithPilot(59),
		n16apsk28x45Normal(60),
		n16apsk28x45NormalWithPilot(61),
		n16apsk23x36Normal(62),
		n16apsk23x36NormalWithPilot(63),
		n16apsk2x3LNormal(64),
		n16apsk2x3LNormalWithPilot(65),
		n16apsk2x3Normal(66),
		n16apsk2x3NormalWithPilot(67),
		n16apsk25x36Normal(68),
		n16apsk25x36NormalWithPilot(69),
		n16apsk13x18Normal(70),
		n16apsk13x18NormalWithPilot(71),
		n16apsk3x4NormalWithPilot(72),
		n16apsk7x9Normal(73),
		n16apsk7x9NormalWithPilot(74),
		n16apsk4x5Normal(75),
		n16apsk4x5NormalWithPilot(76),
		n16apsk5x6Normal(77),
		n16apsk5x6NormalWithPilot(78),
		n16apsk77x90Normal(79),
		n16apsk77x90NormalWithPilot(80),
		n16apsk8x9Normal(81),
		n16apsk8x9NormalWithPilot(82),
		n16apsk9x10Normal(83),
		n16apsk9x10NormalWithPilot(84),
		n32apsk2x3LNormal(85),
		n32apsk2x3LNormalWithPilot(86),
		n32apsk32x45Normal(87),
		n32apsk32x45NormalWithPilot(88),
		n32apsk11x15Normal(89),
		n32apsk11x15NormalWithPilot(90),
		n32apsk3x4Normal(91),
		n32apsk3x4NormalWithPilot(92),
		n32apsk7x9Normal(93),
		n32apsk7x9NormalWithPilot(94),
		n32apsk4x5NormalWithPilot(95),
		n32apsk5x6Normal(96),
		n32apsk5x6NormalWithPilot(97),
		n32apsk8x9Normal(98),
		n32apsk8x9NormalWithPilot(99),
		n32apsk9x10Normal(100),
		n32apsk9x10NormalWithPilot(101),
		n64apsk32x45LNormal(102),
		n64apsk32x45LNormalWithPilot(103),
		n64apsk11x15Normal(104),
		n64apsk11x15NormalWithPilot(105),
		n64apsk7x9Normal(106),
		n64apsk7x9NormalWithPilot(107),
		n64apsk4x5Normal(108),
		n64apsk4x5NormalWithPilot(109),
		n64apsk5x6Normal(110),
		n64apsk5x6NormalWithPilot(111),
		n128apsk3x4Normal(112),
		n128apsk3x4NormalWithPilot(113),
		n128apsk7x9Normal(114),
		n128apsk7x9NormalWithPilot(115),
		n256apsk29x45LNormal(116),
		n256apsk29x45LNormalWithPilot(117),
		n256apsk2x3LNormal(118),
		n256apsk2x3LNormalWithPilot(119),
		n256apsk31x45LNormal(120),
		n256apsk31x45LNormalWithPilot(121),
		n256apsk32x45Normal(122),
		n256apsk32x45NormalWithPilot(123),
		n256apsk11x15LNormal(124),
		n256apsk11x15LNormalWithPilot(125),
		n256apsk3x4Normal(126),
		n256apsk3x4NormalWithPilot(127),
		qpsk1x4Short(128),
		qpsk1x4ShortWithPilot(129),
		qpsk11x45Short(130),
		qpsk11x45ShortWithPilot(131),
		qpsk4x15Short(132),
		qpsk4x15ShortWithPilot(133),
		qpsk14x45Short(134),
		qpsk14x45ShortWithPilot(135),
		qpsk1x3Short(136),
		qpsk1x3ShortWithPilot(137),
		qpsk2x5Short(138),
		qpsk2x5ShortWithPilot(139),
		qpsk1x2Short(140),
		qpsk1x2ShortWithPilot(141),
		qpsk7x15Short(142),
		qpsk7x15ShortWithPilot(143),
		qpsk8x15Short(144),
		qpsk8x15ShortWithPilot(145),
		qpsk3x5Short(146),
		qpsk3x5ShortWithPilot(147),
		qpsk2x3Short(148),
		qpsk2x3ShortWithPilot(149),
		qpsk32x45Short(150),
		qpsk32x45ShortWithPilot(151),
		qpsk3x4Short(152),
		qpsk3x4ShortWithPilot(153),
		qpsk4x5Short(154),
		qpsk4x5ShortWithPilot(155),
		qpsk5x6Short(156),
		qpsk5x6ShortWithPilot(157),
		qpsk8x9Short(158),
		qpsk8x9ShortWithPilot(159),
		n8psk7x15Short(160),
		n8psk7x15ShortWithPilot(161),
		n8psk8x15Short(162),
		n8psk8x15ShortWithPilot(163),
		n8psk26x45Short(164),
		n8psk26x45ShortWithPilot(165),
		n8psk3x5ShortWithPilot(166),
		n8psk2x3ShortWithPilot(167),
		n8psk32x45Short(168),
		n8psk32x45ShortWithPilot(169),
		n8psk3x4Short(170),
		n8psk3x4ShortWithPilot(171),
		n8psk5x6Short(172),
		n8psk5x6ShortWithPilot(173),
		n8psk8x9Short(174),
		n8psk8x9ShortWithPilot(175),
		n16apsk7x15Short(176),
		n16apsk7x15ShortWithPilot(177),
		n16apsk8x15Short(178),
		n16apsk8x15ShortWithPilot(179),
		n16apsk26x45Short(180),
		n16apsk26x45ShortWithPilot(181),
		n16apsk3x5Short(182),
		n16apsk3x5ShortWithPilot(183),
		n16apsk2x3Short(184),
		n16apsk2x3ShortWithPilot(185),
		n16apsk32x45Short(186),
		n16apsk32x45ShortWithPilot(187)
	}
	MAX-ACCESS	read-only
	STATUS		current
	DESCRIPTION "Tx ModCod, where:
			    0) 'QPSK 1/4 Normal'
			    1) 'QPSK 1/4 Normal with Pilot'
			    2) 'QPSK 13/45 Normal'
			    3) 'QPSK 13/45 Normal with Pilot'
			    4) 'QPSK 1/3 Normal'
			    5) 'QPSK 1/3 Normal with Pilot'
			    6) 'QPSK 2/5 Normal'
			    7) 'QPSK 2/5 Normal with Pilot'
			    8) 'QPSK 9/20 Normal'
			    9) 'QPSK 9/20 Normal with Pilot'
			    10) 'QPSK 1/2 Normal'
			    11) 'QPSK 1/2 Normal with Pilot'
			    12) 'QPSK 11/20 Normal'
			    13) 'QPSK 11/20 Normal with Pilot'
			    14) 'QPSK 3/5 Normal'
			    15) 'QPSK 3/5 Normal with Pilot'
			    16) 'QPSK 2/3 Normal'
			    17) 'QPSK 2/3 Normal with Pilot'
			    18) 'QPSK 3/4 Normal'
			    19) 'QPSK 3/4 Normal with Pilot'
			    20) 'QPSK 4/5 Normal'
			    21) 'QPSK 4/5 Normal with Pilot'
			    22) 'QPSK 5/6 Normal'
			    23) 'QPSK 5/6 Normal with Pilot'
			    24) 'QPSK 8/9 Normal'
			    25) 'QPSK 8/9 Normal with Pilot'
			    26) 'QPSK 9/10 Normal'
			    27) 'QPSK 9/10 Normal with Pilot'
			    28) '8APSK 5/9-L Normal'
			    29) '8APSK 5/9-L Normal with Pilot'
			    30) '8APSK 26/45-L Normal'
			    31) '8APSK 26/45-L Normal with Pilot'
			    32) '8PSK 3/5 Normal with Pilot'
			    33) '8PSK 23/36 Normal'
			    34) '8PSK 23/36 Normal with Pilot'
			    35) '8PSK 2/3 Normal with Pilot'
			    36) '8PSK 25/36 Normal'
			    37) '8PSK 25/36 Normal with Pilot'
			    38) '8PSK 13/18 Normal'
			    39) '8PSK 13/18 Normal with Pilot'
			    40) '8PSK 3/4 Normal'
			    41) '8PSK 3/4 Normal with Pilot'
			    42) '8PSK 5/6 Normal'
			    43) '8PSK 5/6 Normal with Pilot'
			    44) '8PSK 8/9 Normal'
			    45) '8PSK 8/9 Normal with Pilot'
			    46) '8PSK 9/10 Normal'
			    47) '8PSK 9/10 Normal with Pilot'
			    48) '16APSK 1/2-L Normal'
			    49) '16APSK 1/2-L Normal with Pilot'
			    50) '16APSK 8/15-L Normal'
			    51) '16APSK 8/15-L Normal with Pilot'
			    52) '16APSK 5/9-L Normal'
			    53) '16APSK 5/9-L Normal with Pilot'
			    54) '16APSK 26/45 Normal'
			    55) '16APSK 26/45 Normal with Pilot'
			    56) '16APSK 3/5 Normal'
			    57) '16APSK 3/5 Normal with Pilot'
			    58) '16APSK 3/5-L Normal'
			    59) '16APSK 3/5-L Normal with Pilot'
			    60) '16APSK 28/45 Normal'
			    61) '16APSK 28/45 Normal with Pilot'
			    62) '16APSK 23/36 Normal'
			    63) '16APSK 23/36 Normal with Pilot'
			    64) '16APSK 2/3-L Normal'
			    65) '16APSK 2/3-L Normal with Pilot'
			    66) '16APSK 2/3 Normal'
			    67) '16APSK 2/3 Normal with Pilot'
			    68) '16APSK 25/36 Normal'
			    69) '16APSK 25/36 Normal with Pilot'
			    70) '16APSK 13/18 Normal'
			    71) '16APSK 13/18 Normal with Pilot'
			    72) '16APSK 3/4 Normal with Pilot'
			    73) '16APSK 7/9 Normal'
			    74) '16APSK 7/9 Normal with Pilot'
			    75) '16APSK 4/5 Normal'
			    76) '16APSK 4/5 Normal with Pilot'
			    77) '16APSK 5/6 Normal'
			    78) '16APSK 5/6 Normal with Pilot'
			    79) '16APSK 77/90 Normal'
			    80) '16APSK 77/90 Normal with Pilot'
			    81) '16APSK 8/9 Normal'
			    82) '16APSK 8/9 Normal with Pilot'
			    83) '16APSK 9/10 Normal'
			    84) '16APSK 9/10 Normal with Pilot'
			    85) '32APSK 2/3-L Normal'
			    86) '32APSK 2/3-L Normal with Pilot'
			    87) '32APSK 32/45 Normal'
			    88) '32APSK 32/45 Normal with Pilot'
			    89) '32APSK 11/15 Normal'
			    90) '32APSK 11/15 Normal with Pilot'
			    91) '32APSK 3/4 Normal'
			    92) '32APSK 3/4 Normal with Pilot'
			    93) '32APSK 7/9 Normal'
			    94) '32APSK 7/9 Normal with Pilot'
			    95) '32APSK 4/5 Normal with Pilot'
			    96) '32APSK 5/6 Normal'
			    97) '32APSK 5/6 Normal with Pilot'
			    98) '32APSK 8/9 Normal'
			    99) '32APSK 8/9 Normal with Pilot'
			    100) '32APSK 9/10 Normal'
			    101) '32APSK 9/10 Normal with Pilot'
			    102) '64APSK 32/45-L Normal'
			    103) '64APSK 32/45-L Normal with Pilot'
			    104) '64APSK 11/15 Normal'
			    105) '64APSK 11/15 Normal with Pilot'
			    106) '64APSK 7/9 Normal'
			    107) '64APSK 7/9 Normal with Pilot'
			    108) '64APSK 4/5 Normal'
			    109) '64APSK 4/5 Normal with Pilot'
			    110) '64APSK 5/6 Normal'
			    111) '64APSK 5/6 Normal with Pilot'
			    112) '128APSK 3/4 Normal'
			    113) '128APSK 3/4 Normal with Pilot'
			    114) '128APSK 7/9 Normal'
			    115) '128APSK 7/9 Normal with Pilot'
			    116) '256APSK 29/45-L Normal'
			    117) '256APSK 29/45-L Normal with Pilot'
			    118) '256APSK 2/3-L Normal'
			    119) '256APSK 2/3-L Normal with Pilot'
			    120) '256APSK 31/45-L Normal'
			    121) '256APSK 31/45-L Normal with Pilot'
			    122) '256APSK 32/45 Normal'
			    123) '256APSK 32/45 Normal with Pilot'
			    124) '256APSK 11/15-L Normal'
			    125) '256APSK 11/15-L Normal with Pilot'
			    126) '256APSK 3/4 Normal'
			    127) '256APSK 3/4 Normal with Pilot'
			    128) 'QPSK 1/4 Short'
			    129) 'QPSK 1/4 Short with Pilot'
			    130) 'QPSK 11/45 Short'
			    131) 'QPSK 11/45 Short with Pilot'
			    132) 'QPSK 4/15 Short'
			    133) 'QPSK 4/15 Short with Pilot'
			    134) 'QPSK 14/45 Short'
			    135) 'QPSK 14/45 Short with Pilot'
			    136) 'QPSK 1/3 Short'
			    137) 'QPSK 1/3 Short with Pilot'
			    138) 'QPSK 2/5 Short'
			    139) 'QPSK 2/5 Short with Pilot'
			    140) 'QPSK 1/2 Short'
			    141) 'QPSK 1/2 Short with Pilot'
			    142) 'QPSK 7/15 Short'
			    143) 'QPSK 7/15 Short with Pilot'
			    144) 'QPSK 8/15 Short'
			    145) 'QPSK 8/15 Short with Pilot'
			    146) 'QPSK 3/5 Short'
			    147) 'QPSK 3/5 Short with Pilot'
			    148) 'QPSK 2/3 Short'
			    149) 'QPSK 2/3 Short with Pilot'
			    150) 'QPSK 32/45 Short'
			    151) 'QPSK 32/45 Short with Pilot'
			    152) 'QPSK 3/4 Short'
			    153) 'QPSK 3/4 Short with Pilot'
			    154) 'QPSK 4/5 Short'
			    155) 'QPSK 4/5 Short with Pilot'
			    156) 'QPSK 5/6 Short'
			    157) 'QPSK 5/6 Short with Pilot'
			    158) 'QPSK 8/9 Short'
			    159) 'QPSK 8/9 Short with Pilot'
			    160) '8PSK 7/15 Short'
			    161) '8PSK 7/15 Short with Pilot'
			    162) '8PSK 8/15 Short'
			    163) '8PSK 8/15 Short with Pilot'
			    164) '8PSK 26/45 Short'
			    165) '8PSK 26/45 Short with Pilot'
			    166) '8PSK 3/5 Short with Pilot'
			    167) '8PSK 2/3 Short with Pilot'
			    168) '8PSK 32/45 Short'
			    169) '8PSK 32/45 Short with Pilot'
			    170) '8PSK 3/4 Short'
			    171) '8PSK 3/4 Short with Pilot'
			    172) '8PSK 5/6 Short'
			    173) '8PSK 5/6 Short with Pilot'
			    174) '8PSK 8/9 Short'
			    175) '8PSK 8/9 Short with Pilot'
			    176) '16APSK 7/15 Short'
			    177) '16APSK 7/15 Short with Pilot'
			    178) '16APSK 8/15 Short'
			    179) '16APSK 8/15 Short with Pilot'
			    180) '16APSK 26/45 Short'
			    181) '16APSK 26/45 Short with Pilot'
			    182) '16APSK 3/5 Short'
			    183) '16APSK 3/5 Short with Pilot'
			    184) '16APSK 2/3 Short'
			    185) '16APSK 2/3 Short with Pilot'
			    186) '16APSK 32/45 Short'
			    187) '16APSK 32/45 Short with Pilot'
			Oid=1.3.6.1.4.1.31968.3.1.4.1.7.3
			"
	::= { txStatusItems 3 }

txLdpcModcod OBJECT-TYPE
	SYNTAX		INTEGER {
		bpsk1x2(0),
		bpsk8x15(1),
		bpsk4x7(2),
		bpsk8x13(3),
		bpsk2x3(4),
		bpsk16x23(5),
		bpsk8x11(6),
		qpsk1x2(7),
		qpsk8x15(8),
		qpsk4x7(9),
		qpsk8x13(10),
		qpsk2x3(11),
		qpsk16x23(12),
		qpsk8x11(13),
		qpsk16x21(14),
		qpsk4x5(15),
		qpsk16x19(16),
		qpsk8x9(17),
		n8psk8x13(18),
		n8psk2x3(19),
		n8psk16x23(20),
		n8apsk8x13(21),
		n8apsk2x3(22),
		n8apsk16x23(23),
		n16apsk4x7(24),
		n16apsk8x13(25),
		n16apsk2x3(26),
		n16apsk16x23(27),
		n16apsk8x11(28),
		n16apsk16x21(29),
		n16apsk4x5(30),
		n16apsk16x19(31),
		n16apsk8x9(32),
		n16apsk16x17(33),
		n16qam1x2(34),
		n16qam8x15(35),
		n16qam4x7(36),
		n16qam8x13(37),
		n16qam2x3(38),
		n16qam16x23(39),
		n16qam8x11(40),
		n16qam16x21(41),
		n16qam4x5(42),
		n16qam16x19(43),
		n16qam8x9(44),
		n16qam16x17(45),
		n32qam2x3(46),
		n32qam16x23(47),
		n32qam8x11(48),
		n32qam16x21(49),
		n32qam4x5(50),
		n32qam16x19(51),
		n32qam8x9(52),
		n32qam16x17(53),
		n64qam2x3(54),
		n64qam16x23(55),
		n64qam8x11(56),
		n64qam16x21(57),
		n64qam4x5(58),
		n64qam16x19(59),
		n64qam8x9(60),
		n64qam16x17(61)
	}
	MAX-ACCESS	read-only
	STATUS		current
	DESCRIPTION "Tx ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'QPSK 1/2'
			    8) 'QPSK 8/15'
			    9) 'QPSK 4/7'
			    10) 'QPSK 8/13'
			    11) 'QPSK 2/3'
			    12) 'QPSK 16/23'
			    13) 'QPSK 8/11'
			    14) 'QPSK 16/21'
			    15) 'QPSK 4/5'
			    16) 'QPSK 16/19'
			    17) 'QPSK 8/9'
			    18) '8PSK 8/13'
			    19) '8PSK 2/3'
			    20) '8PSK 16/23'
			    21) '8APSK 8/13'
			    22) '8APSK 2/3'
			    23) '8APSK 16/23'
			    24) '16APSK 4/7'
			    25) '16APSK 8/13'
			    26) '16APSK 2/3'
			    27) '16APSK 16/23'
			    28) '16APSK 8/11'
			    29) '16APSK 16/21'
			    30) '16APSK 4/5'
			    31) '16APSK 16/19'
			    32) '16APSK 8/9'
			    33) '16APSK 16/17'
			    34) '16QAM 1/2'
			    35) '16QAM 8/15'
			    36) '16QAM 4/7'
			    37) '16QAM 8/13'
			    38) '16QAM 2/3'
			    39) '16QAM 16/23'
			    40) '16QAM 8/11'
			    41) '16QAM 16/21'
			    42) '16QAM 4/5'
			    43) '16QAM 16/19'
			    44) '16QAM 8/9'
			    45) '16QAM 16/17'
			    46) '32QAM 2/3'
			    47) '32QAM 16/23'
			    48) '32QAM 8/11'
			    49) '32QAM 16/21'
			    50) '32QAM 4/5'
			    51) '32QAM 16/19'
			    52) '32QAM 8/9'
			    53) '32QAM 16/17'
			    54) '64QAM 2/3'
			    55) '64QAM 16/23'
			    56) '64QAM 8/11'
			    57) '64QAM 16/21'
			    58) '64QAM 4/5'
			    59) '64QAM 16/19'
			    60) '64QAM 8/9'
			    61) '64QAM 16/17'
			Oid=1.3.6.1.4.1.31968.3.1.4.1.7.4
			"
	::= { txStatusItems 4 }

txRemoteEsn0 OBJECT-TYPE
	SYNTAX		Integer32
	UNITS		"0.01 dB"
	MAX-ACCESS	read-only
	STATUS		current
	DESCRIPTION "Tx Remote Es/N0
			Oid=1.3.6.1.4.1.31968.3.1.4.1.7.5
			"
	::= { txStatusItems 5 }

txFeatureBitRateLimit OBJECT-TYPE
	SYNTAX		Unsigned32
	UNITS		"1 bps"
	MAX-ACCESS	read-only
	STATUS		current
	DESCRIPTION "Tx Bit Rate Limit
			Oid=1.3.6.1.4.1.31968.3.1.4.1.7.6
			"
	::= { txStatusItems 6 }

txFeatureSymbolRateLimit OBJECT-TYPE
	SYNTAX		Unsigned32
	UNITS		"1 sps"
	MAX-ACCESS	read-only
	STATUS		current
	DESCRIPTION "Tx Symbol/Chip Rate Limit
			Oid=1.3.6.1.4.1.31968.3.1.4.1.7.7
			"
	::= { txStatusItems 7 }

txFeatureSmartCarrierBitRateLimit OBJECT-TYPE
	SYNTAX		Unsigned32
	UNITS		"1 bps"
	MAX-ACCESS	read-only
	STATUS		current
	DESCRIPTION "Tx Smart Cxr Bit Rate Limit
			Oid=1.3.6.1.4.1.31968.3.1.4.1.7.8
			"
	::= { txStatusItems 8 }

txFeatureSmartCarrierSymbolRateLimit OBJECT-TYPE
	SYNTAX		Unsigned32
	UNITS		"1 sps"
	MAX-ACCESS	read-only
	STATUS		current
	DESCRIPTION "Tx Smart Cxr Symbol Rate Limit
			Oid=1.3.6.1.4.1.31968.3.1.4.1.7.9
			"
	::= { txStatusItems 9 }

txFeatureModulationLimit OBJECT-TYPE
	SYNTAX		INTEGER {
		n4Ary(0),
		n8Ary(1),
		n16Ary(2),
		n32Ary(3),
		n64Ary(4),
		n128Ary(5),
		n256Ary(6),
		n512Ary(7)
	}
	MAX-ACCESS	read-only
	STATUS		current
	DESCRIPTION "Tx Modulation Limit, where:
			    0) '4-ary'
			    1) '8-ary'
			    2) '16-ary'
			    3) '32-ary'
			    4) '64-ary'
			    5) '128-ary'
			    6) '256-ary'
			    7) '512-ary'
			Oid=1.3.6.1.4.1.31968.3.1.4.1.7.10
			"
	::= { txStatusItems 10 }

txFeatureChannelLimit OBJECT-TYPE
	SYNTAX		Unsigned32
	UNITS		"1"
	MAX-ACCESS	read-only
	STATUS		current
	DESCRIPTION "Tx Channel Limit
			Oid=1.3.6.1.4.1.31968.3.1.4.1.7.11
			"
	::= { txStatusItems 11 }

txFeatureWaveforms OBJECT-TYPE
	SYNTAX		DisplayString
	MAX-ACCESS	read-only
	STATUS		current
	DESCRIPTION "Tx Waveforms
			Oid=1.3.6.1.4.1.31968.3.1.4.1.7.12
			"
	::= { txStatusItems 12 }

txFeatureTransec OBJECT-TYPE
	SYNTAX		INTEGER {
		none(0),
		aes128(1),
		aes128Aes192(2),
		aes128Aes192Aes256(3)
	}
	MAX-ACCESS	read-only
	STATUS		current
	DESCRIPTION "Tx TRANSEC, where:
			    0) 'None'
			    1) 'AES-128'
			    2) 'AES-128, AES-192'
			    3) 'AES-128, AES-192, AES-256'
			Oid=1.3.6.1.4.1.31968.3.1.4.1.7.13
			"
	::= { txStatusItems 13 }

txTotalSymbolRate OBJECT-TYPE
	SYNTAX		Unsigned32
	UNITS		"1 sps"
	MAX-ACCESS	read-only
	STATUS		current
	DESCRIPTION "Tx Total Symbol Rate
			Oid=1.3.6.1.4.1.31968.3.1.4.1.7.19
			"
	::= { txStatusItems 19 }

txQueue0DataRate OBJECT-TYPE
	SYNTAX		Unsigned32
	UNITS		"1 bps"
	MAX-ACCESS	read-only
	STATUS		current
	DESCRIPTION "Tx Queue 0 Data Rate
			Oid=1.3.6.1.4.1.31968.3.1.4.1.7.20
			"
	::= { txStatusItems 20 }

txQueue0AverageRate OBJECT-TYPE
	SYNTAX		Unsigned32
	UNITS		"1 bps"
	MAX-ACCESS	read-only
	STATUS		current
	DESCRIPTION "Tx Queue 0 Average Data Rate
			Oid=1.3.6.1.4.1.31968.3.1.4.1.7.21
			"
	::= { txStatusItems 21 }

txQueue0Sent OBJECT-TYPE
	SYNTAX		DisplayString(SIZE(1..24))
	UNITS		"1"
	MAX-ACCESS	read-only
	STATUS		current
	DESCRIPTION "Tx Queue 0 Packets Sent,
			    Text Number, Decimal
			Oid=1.3.6.1.4.1.31968.3.1.4.1.7.22
			"
	::= { txStatusItems 22 }

txQueue0Dropped OBJECT-TYPE
	SYNTAX		DisplayString(SIZE(1..24))
	UNITS		"1"
	MAX-ACCESS	read-only
	STATUS		current
	DESCRIPTION "Tx Queue 0 Live Pckts Dropped,
			    Text Number, Decimal
			Oid=1.3.6.1.4.1.31968.3.1.4.1.7.23
			"
	::= { txStatusItems 23 }

txQueue1DataRate OBJECT-TYPE
	SYNTAX		Unsigned32
	UNITS		"1 bps"
	MAX-ACCESS	read-only
	STATUS		current
	DESCRIPTION "Tx Queue 1 Data Rate
			Oid=1.3.6.1.4.1.31968.3.1.4.1.7.24
			"
	::= { txStatusItems 24 }

txQueue1AverageRate OBJECT-TYPE
	SYNTAX		Unsigned32
	UNITS		"1 bps"
	MAX-ACCESS	read-only
	STATUS		current
	DESCRIPTION "Tx Queue 1 Average Data Rate
			Oid=1.3.6.1.4.1.31968.3.1.4.1.7.25
			"
	::= { txStatusItems 25 }

txQueue1Sent OBJECT-TYPE
	SYNTAX		DisplayString(SIZE(1..24))
	UNITS		"1"
	MAX-ACCESS	read-only
	STATUS		current
	DESCRIPTION "Tx Queue 1 Packets Sent,
			    Text Number, Decimal
			Oid=1.3.6.1.4.1.31968.3.1.4.1.7.26
			"
	::= { txStatusItems 26 }

txQueue1Dropped OBJECT-TYPE
	SYNTAX		DisplayString(SIZE(1..24))
	UNITS		"1"
	MAX-ACCESS	read-only
	STATUS		current
	DESCRIPTION "Tx Queue 1 Live Pckts Dropped,
			    Text Number, Decimal
			Oid=1.3.6.1.4.1.31968.3.1.4.1.7.27
			"
	::= { txStatusItems 27 }

txQueue2DataRate OBJECT-TYPE
	SYNTAX		Unsigned32
	UNITS		"1 bps"
	MAX-ACCESS	read-only
	STATUS		current
	DESCRIPTION "Tx Queue 2 Data Rate
			Oid=1.3.6.1.4.1.31968.3.1.4.1.7.28
			"
	::= { txStatusItems 28 }

txQueue2AverageRate OBJECT-TYPE
	SYNTAX		Unsigned32
	UNITS		"1 bps"
	MAX-ACCESS	read-only
	STATUS		current
	DESCRIPTION "Tx Queue 2 Average Data Rate
			Oid=1.3.6.1.4.1.31968.3.1.4.1.7.29
			"
	::= { txStatusItems 29 }

txQueue2Sent OBJECT-TYPE
	SYNTAX		DisplayString(SIZE(1..24))
	UNITS		"1"
	MAX-ACCESS	read-only
	STATUS		current
	DESCRIPTION "Tx Queue 2 Packets Sent,
			    Text Number, Decimal
			Oid=1.3.6.1.4.1.31968.3.1.4.1.7.30
			"
	::= { txStatusItems 30 }

txQueue2Dropped OBJECT-TYPE
	SYNTAX		DisplayString(SIZE(1..24))
	UNITS		"1"
	MAX-ACCESS	read-only
	STATUS		current
	DESCRIPTION "Tx Queue 2 Live Pckts Dropped,
			    Text Number, Decimal
			Oid=1.3.6.1.4.1.31968.3.1.4.1.7.31
			"
	::= { txStatusItems 31 }

txQueue3DataRate OBJECT-TYPE
	SYNTAX		Unsigned32
	UNITS		"1 bps"
	MAX-ACCESS	read-only
	STATUS		current
	DESCRIPTION "Tx Queue 3 Data Rate
			Oid=1.3.6.1.4.1.31968.3.1.4.1.7.32
			"
	::= { txStatusItems 32 }

txQueue3AverageRate OBJECT-TYPE
	SYNTAX		Unsigned32
	UNITS		"1 bps"
	MAX-ACCESS	read-only
	STATUS		current
	DESCRIPTION "Tx Queue 3 Average Data Rate
			Oid=1.3.6.1.4.1.31968.3.1.4.1.7.33
			"
	::= { txStatusItems 33 }

txQueue3Sent OBJECT-TYPE
	SYNTAX		DisplayString(SIZE(1..24))
	UNITS		"1"
	MAX-ACCESS	read-only
	STATUS		current
	DESCRIPTION "Tx Queue 3 Packets Sent,
			    Text Number, Decimal
			Oid=1.3.6.1.4.1.31968.3.1.4.1.7.34
			"
	::= { txStatusItems 34 }

txQueue3Dropped OBJECT-TYPE
	SYNTAX		DisplayString(SIZE(1..24))
	UNITS		"1"
	MAX-ACCESS	read-only
	STATUS		current
	DESCRIPTION "Tx Queue 3 Live Pckts Dropped,
			    Text Number, Decimal
			Oid=1.3.6.1.4.1.31968.3.1.4.1.7.35
			"
	::= { txStatusItems 35 }

txQueue4DataRate OBJECT-TYPE
	SYNTAX		Unsigned32
	UNITS		"1 bps"
	MAX-ACCESS	read-only
	STATUS		current
	DESCRIPTION "Tx Queue 4 Data Rate
			Oid=1.3.6.1.4.1.31968.3.1.4.1.7.36
			"
	::= { txStatusItems 36 }

txQueue4AverageRate OBJECT-TYPE
	SYNTAX		Unsigned32
	UNITS		"1 bps"
	MAX-ACCESS	read-only
	STATUS		current
	DESCRIPTION "Tx Queue 4 Average Data Rate
			Oid=1.3.6.1.4.1.31968.3.1.4.1.7.37
			"
	::= { txStatusItems 37 }

txQueue4Sent OBJECT-TYPE
	SYNTAX		DisplayString(SIZE(1..24))
	UNITS		"1"
	MAX-ACCESS	read-only
	STATUS		current
	DESCRIPTION "Tx Queue 4 Packets Sent,
			    Text Number, Decimal
			Oid=1.3.6.1.4.1.31968.3.1.4.1.7.38
			"
	::= { txStatusItems 38 }

txQueue4Dropped OBJECT-TYPE
	SYNTAX		DisplayString(SIZE(1..24))
	UNITS		"1"
	MAX-ACCESS	read-only
	STATUS		current
	DESCRIPTION "Tx Queue 4 Live Pckts Dropped,
			    Text Number, Decimal
			Oid=1.3.6.1.4.1.31968.3.1.4.1.7.39
			"
	::= { txStatusItems 39 }

txQueue5DataRate OBJECT-TYPE
	SYNTAX		Unsigned32
	UNITS		"1 bps"
	MAX-ACCESS	read-only
	STATUS		current
	DESCRIPTION "Tx Queue 5 Data Rate
			Oid=1.3.6.1.4.1.31968.3.1.4.1.7.40
			"
	::= { txStatusItems 40 }

txQueue5AverageRate OBJECT-TYPE
	SYNTAX		Unsigned32
	UNITS		"1 bps"
	MAX-ACCESS	read-only
	STATUS		current
	DESCRIPTION "Tx Queue 5 Average Data Rate
			Oid=1.3.6.1.4.1.31968.3.1.4.1.7.41
			"
	::= { txStatusItems 41 }

txQueue5Sent OBJECT-TYPE
	SYNTAX		DisplayString(SIZE(1..24))
	UNITS		"1"
	MAX-ACCESS	read-only
	STATUS		current
	DESCRIPTION "Tx Queue 5 Packets Sent,
			    Text Number, Decimal
			Oid=1.3.6.1.4.1.31968.3.1.4.1.7.42
			"
	::= { txStatusItems 42 }

txQueue5Dropped OBJECT-TYPE
	SYNTAX		DisplayString(SIZE(1..24))
	UNITS		"1"
	MAX-ACCESS	read-only
	STATUS		current
	DESCRIPTION "Tx Queue 5 Live Pckts Dropped,
			    Text Number, Decimal
			Oid=1.3.6.1.4.1.31968.3.1.4.1.7.43
			"
	::= { txStatusItems 43 }

txQueue6DataRate OBJECT-TYPE
	SYNTAX		Unsigned32
	UNITS		"1 bps"
	MAX-ACCESS	read-only
	STATUS		current
	DESCRIPTION "Tx Queue 6 Data Rate
			Oid=1.3.6.1.4.1.31968.3.1.4.1.7.44
			"
	::= { txStatusItems 44 }

txQueue6AverageRate OBJECT-TYPE
	SYNTAX		Unsigned32
	UNITS		"1 bps"
	MAX-ACCESS	read-only
	STATUS		current
	DESCRIPTION "Tx Queue 6 Average Data Rate
			Oid=1.3.6.1.4.1.31968.3.1.4.1.7.45
			"
	::= { txStatusItems 45 }

txQueue6Dropped OBJECT-TYPE
	SYNTAX		DisplayString(SIZE(1..24))
	UNITS		"1"
	MAX-ACCESS	read-only
	STATUS		current
	DESCRIPTION "Tx Queue 6 Live Pckts Dropped,
			    Text Number, Decimal
			Oid=1.3.6.1.4.1.31968.3.1.4.1.7.46
			"
	::= { txStatusItems 46 }

txQueue7DataRate OBJECT-TYPE
	SYNTAX		Unsigned32
	UNITS		"1 bps"
	MAX-ACCESS	read-only
	STATUS		current
	DESCRIPTION "Tx Queue 7 Data Rate
			Oid=1.3.6.1.4.1.31968.3.1.4.1.7.47
			"
	::= { txStatusItems 47 }

txQueue7AverageRate OBJECT-TYPE
	SYNTAX		Unsigned32
	UNITS		"1 bps"
	MAX-ACCESS	read-only
	STATUS		current
	DESCRIPTION "Tx Queue 7 Average Data Rate
			Oid=1.3.6.1.4.1.31968.3.1.4.1.7.48
			"
	::= { txStatusItems 48 }

txQueue7Sent OBJECT-TYPE
	SYNTAX		DisplayString(SIZE(1..24))
	UNITS		"1"
	MAX-ACCESS	read-only
	STATUS		current
	DESCRIPTION "Tx Queue 7 Packets Sent,
			    Text Number, Decimal
			Oid=1.3.6.1.4.1.31968.3.1.4.1.7.49
			"
	::= { txStatusItems 49 }

txQueue7Dropped OBJECT-TYPE
	SYNTAX		DisplayString(SIZE(1..24))
	UNITS		"1"
	MAX-ACCESS	read-only
	STATUS		current
	DESCRIPTION "Tx Queue 7 Live Pckts Dropped,
			    Text Number, Decimal
			Oid=1.3.6.1.4.1.31968.3.1.4.1.7.50
			"
	::= { txStatusItems 50 }

txEchoDrops OBJECT-TYPE
	SYNTAX		DisplayString(SIZE(1..24))
	UNITS		"1"
	MAX-ACCESS	read-only
	STATUS		current
	DESCRIPTION "Tx Echo Drops,
			    Text Number, Decimal
			Oid=1.3.6.1.4.1.31968.3.1.4.1.7.52
			"
	::= { txStatusItems 52 }

txRate OBJECT-TYPE
	SYNTAX		Unsigned32
	UNITS		"1 bps"
	MAX-ACCESS	read-only
	STATUS		current
	DESCRIPTION "Tx Data Rate
			Oid=1.3.6.1.4.1.31968.3.1.4.1.7.53
			"
	::= { txStatusItems 53 }

txAverageRate OBJECT-TYPE
	SYNTAX		Unsigned32
	UNITS		"1 bps"
	MAX-ACCESS	read-only
	STATUS		current
	DESCRIPTION "Tx Average Data Rate
			Oid=1.3.6.1.4.1.31968.3.1.4.1.7.54
			"
	::= { txStatusItems 54 }

txPps OBJECT-TYPE
	SYNTAX		Unsigned32
	UNITS		"1 pps"
	MAX-ACCESS	read-only
	STATUS		current
	DESCRIPTION "Tx Data PPS
			Oid=1.3.6.1.4.1.31968.3.1.4.1.7.55
			"
	::= { txStatusItems 55 }

txAveragePps OBJECT-TYPE
	SYNTAX		Unsigned32
	UNITS		"1 pps"
	MAX-ACCESS	read-only
	STATUS		current
	DESCRIPTION "Tx Average Data PPS
			Oid=1.3.6.1.4.1.31968.3.1.4.1.7.56
			"
	::= { txStatusItems 56 }

txDataPackets OBJECT-TYPE
	SYNTAX		DisplayString(SIZE(1..24))
	UNITS		"1"
	MAX-ACCESS	read-only
	STATUS		current
	DESCRIPTION "Tx Data Packets,
			    Text Number, Decimal
			Oid=1.3.6.1.4.1.31968.3.1.4.1.7.57
			"
	::= { txStatusItems 57 }

txDataBytes OBJECT-TYPE
	SYNTAX		DisplayString(SIZE(1..24))
	UNITS		"1"
	MAX-ACCESS	read-only
	STATUS		current
	DESCRIPTION "Tx Data Bytes,
			    Text Number, Decimal
			Oid=1.3.6.1.4.1.31968.3.1.4.1.7.58
			"
	::= { txStatusItems 58 }

txIdlePackets OBJECT-TYPE
	SYNTAX		DisplayString(SIZE(1..24))
	UNITS		"1"
	MAX-ACCESS	read-only
	STATUS		current
	DESCRIPTION "Tx Idle Packets,
			    Text Number, Decimal
			Oid=1.3.6.1.4.1.31968.3.1.4.1.7.59
			"
	::= { txStatusItems 59 }

txIdleBytes OBJECT-TYPE
	SYNTAX		DisplayString(SIZE(1..24))
	UNITS		"1"
	MAX-ACCESS	read-only
	STATUS		current
	DESCRIPTION "Tx Idle Bytes,
			    Text Number, Decimal
			Oid=1.3.6.1.4.1.31968.3.1.4.1.7.60
			"
	::= { txStatusItems 60 }

txMccPackets OBJECT-TYPE
	SYNTAX		DisplayString(SIZE(1..24))
	UNITS		"1"
	MAX-ACCESS	read-only
	STATUS		current
	DESCRIPTION "Tx MCC Packets,
			    Text Number, Decimal
			Oid=1.3.6.1.4.1.31968.3.1.4.1.7.61
			"
	::= { txStatusItems 61 }

txMccBytes OBJECT-TYPE
	SYNTAX		DisplayString(SIZE(1..24))
	UNITS		"1"
	MAX-ACCESS	read-only
	STATUS		current
	DESCRIPTION "Tx MCC Bytes,
			    Text Number, Decimal
			Oid=1.3.6.1.4.1.31968.3.1.4.1.7.62
			"
	::= { txStatusItems 62 }

txAcmPackets OBJECT-TYPE
	SYNTAX		DisplayString(SIZE(1..24))
	UNITS		"1"
	MAX-ACCESS	read-only
	STATUS		current
	DESCRIPTION "Tx ACM/AUPC Packets,
			    Text Number, Decimal
			Oid=1.3.6.1.4.1.31968.3.1.4.1.7.63
			"
	::= { txStatusItems 63 }

txAcmBytes OBJECT-TYPE
	SYNTAX		DisplayString(SIZE(1..24))
	UNITS		"1"
	MAX-ACCESS	read-only
	STATUS		current
	DESCRIPTION "Tx ACM/AUPC Bytes,
			    Text Number, Decimal
			Oid=1.3.6.1.4.1.31968.3.1.4.1.7.64
			"
	::= { txStatusItems 64 }

txTotalPackets OBJECT-TYPE
	SYNTAX		DisplayString(SIZE(1..24))
	UNITS		"1"
	MAX-ACCESS	read-only
	STATUS		current
	DESCRIPTION "Tx Total Packets,
			    Text Number, Decimal
			Oid=1.3.6.1.4.1.31968.3.1.4.1.7.65
			"
	::= { txStatusItems 65 }

txTotalBytes OBJECT-TYPE
	SYNTAX		DisplayString(SIZE(1..24))
	UNITS		"1"
	MAX-ACCESS	read-only
	STATUS		current
	DESCRIPTION "Tx Total Bytes,
			    Text Number, Decimal
			Oid=1.3.6.1.4.1.31968.3.1.4.1.7.66
			"
	::= { txStatusItems 66 }

txDroppedPackets OBJECT-TYPE
	SYNTAX		DisplayString(SIZE(1..24))
	UNITS		"1"
	MAX-ACCESS	read-only
	STATUS		current
	DESCRIPTION "Tx Dropped Packets,
			    Text Number, Decimal
			Oid=1.3.6.1.4.1.31968.3.1.4.1.7.67
			"
	::= { txStatusItems 67 }

txTotalPdr OBJECT-TYPE
	SYNTAX		DisplayString(SIZE(1..12))
	MAX-ACCESS	read-only
	STATUS		current
	DESCRIPTION "Tx Total PDR,
			    Text Number, Decimal Floating Point
			Oid=1.3.6.1.4.1.31968.3.1.4.1.7.68
			"
	::= { txStatusItems 68 }

txTotalSeconds OBJECT-TYPE
	SYNTAX		Unsigned32
	UNITS		"1 s"
	MAX-ACCESS	read-only
	STATUS		current
	DESCRIPTION "Tx Total Seconds
			Oid=1.3.6.1.4.1.31968.3.1.4.1.7.69
			"
	::= { txStatusItems 69 }

txTotalAverage OBJECT-TYPE
	SYNTAX		Unsigned32
	UNITS		"1 bps"
	MAX-ACCESS	read-only
	STATUS		current
	DESCRIPTION "Tx Average Total Rate
			Oid=1.3.6.1.4.1.31968.3.1.4.1.7.70
			"
	::= { txStatusItems 70 }

txTotalRate OBJECT-TYPE
	SYNTAX		Unsigned32
	UNITS		"1 bps"
	MAX-ACCESS	read-only
	STATUS		current
	DESCRIPTION "Tx Total Rate
			Oid=1.3.6.1.4.1.31968.3.1.4.1.7.71
			"
	::= { txStatusItems 71 }

txQueue6Sent OBJECT-TYPE
	SYNTAX		DisplayString(SIZE(1..24))
	UNITS		"1"
	MAX-ACCESS	read-only
	STATUS		current
	DESCRIPTION "Tx Queue 6 Packets Sent,
			    Text Number, Decimal
			Oid=1.3.6.1.4.1.31968.3.1.4.1.7.72
			"
	::= { txStatusItems 72 }

txTotalBitRate OBJECT-TYPE
	SYNTAX		Unsigned32
	UNITS		"1 bps"
	MAX-ACCESS	read-only
	STATUS		current
	DESCRIPTION "Tx Total Bit Rate
			Oid=1.3.6.1.4.1.31968.3.1.4.1.7.73
			"
	::= { txStatusItems 73 }

txQueue0Full OBJECT-TYPE
	SYNTAX		DisplayString(SIZE(1..24))
	UNITS		"1"
	MAX-ACCESS	read-only
	STATUS		current
	DESCRIPTION "Tx Queue 0 Full Pckts Dropped,
			    Text Number, Decimal
			Oid=1.3.6.1.4.1.31968.3.1.4.1.7.75
			"
	::= { txStatusItems 75 }

txQueue1Full OBJECT-TYPE
	SYNTAX		DisplayString(SIZE(1..24))
	UNITS		"1"
	MAX-ACCESS	read-only
	STATUS		current
	DESCRIPTION "Tx Queue 1 Full Pckts Dropped,
			    Text Number, Decimal
			Oid=1.3.6.1.4.1.31968.3.1.4.1.7.76
			"
	::= { txStatusItems 76 }

txQueue2Full OBJECT-TYPE
	SYNTAX		DisplayString(SIZE(1..24))
	UNITS		"1"
	MAX-ACCESS	read-only
	STATUS		current
	DESCRIPTION "Tx Queue 2 Full Pckts Dropped,
			    Text Number, Decimal
			Oid=1.3.6.1.4.1.31968.3.1.4.1.7.77
			"
	::= { txStatusItems 77 }

txQueue3Full OBJECT-TYPE
	SYNTAX		DisplayString(SIZE(1..24))
	UNITS		"1"
	MAX-ACCESS	read-only
	STATUS		current
	DESCRIPTION "Tx Queue 3 Full Pckts Dropped,
			    Text Number, Decimal
			Oid=1.3.6.1.4.1.31968.3.1.4.1.7.78
			"
	::= { txStatusItems 78 }

txQueue4Full OBJECT-TYPE
	SYNTAX		DisplayString(SIZE(1..24))
	UNITS		"1"
	MAX-ACCESS	read-only
	STATUS		current
	DESCRIPTION "Tx Queue 4 Full Pckts Dropped,
			    Text Number, Decimal
			Oid=1.3.6.1.4.1.31968.3.1.4.1.7.79
			"
	::= { txStatusItems 79 }

txQueue5Full OBJECT-TYPE
	SYNTAX		DisplayString(SIZE(1..24))
	UNITS		"1"
	MAX-ACCESS	read-only
	STATUS		current
	DESCRIPTION "Tx Queue 5 Full Pckts Dropped,
			    Text Number, Decimal
			Oid=1.3.6.1.4.1.31968.3.1.4.1.7.80
			"
	::= { txStatusItems 80 }

txQueue6Full OBJECT-TYPE
	SYNTAX		DisplayString(SIZE(1..24))
	UNITS		"1"
	MAX-ACCESS	read-only
	STATUS		current
	DESCRIPTION "Tx Queue 6 Full Pckts Dropped,
			    Text Number, Decimal
			Oid=1.3.6.1.4.1.31968.3.1.4.1.7.81
			"
	::= { txStatusItems 81 }

txQueue7Full OBJECT-TYPE
	SYNTAX		DisplayString(SIZE(1..24))
	UNITS		"1"
	MAX-ACCESS	read-only
	STATUS		current
	DESCRIPTION "Tx Queue 7 Full Pckts Dropped,
			    Text Number, Decimal
			Oid=1.3.6.1.4.1.31968.3.1.4.1.7.82
			"
	::= { txStatusItems 82 }

txTotalOutputLevel OBJECT-TYPE
	SYNTAX		Integer32
	UNITS		"0.01 dBm"
	MAX-ACCESS	read-only
	STATUS		current
	DESCRIPTION "Tx Total Output Level
			Oid=1.3.6.1.4.1.31968.3.1.4.1.7.83
			"
	::= { txStatusItems 83 }

txTransecStatus OBJECT-TYPE
	SYNTAX		INTEGER {
		notInstalled(0),
		temperatureAlarm(1),
		hardwareAlarm(2),
		selfTestFailure(3),
		notOperational(4),
		coIdentifierKeysZeroizedLogAsterisk(10),
		keyNotInitializedLogAsterisk(11),
		dataNotEncryptedLogAsterisk(12),
		errorKeyIndexExpiredLogAsterisk(13),
		dataEncryptedLogAsterisk(14),
		coIdentifierKeysZeroized(20),
		keyNotInitialized(21),
		dataNotEncrypted(22),
		errorKeyIndexExpired(23),
		dataEncrypted(24)
	}
	MAX-ACCESS	read-only
	STATUS		current
	DESCRIPTION "Tx Status, where:
			    0) 'Not Installed'
			    1) 'TEMPERATURE ALARM'
			    2) 'HARDWARE ALARM'
			    3) 'SELF TEST FAILURE'
			    4) 'NOT OPERATIONAL'
			    10) 'CO Identifier/Keys Zeroized, Log*'
			    11) 'KEY NOT INITIALIZED, Log*'
			    12) 'DATA NOT ENCRYPTED, Log*'
			    13) 'ERROR, KEY INDEX EXPIRED, Log*'
			    14) 'Data Encrypted, Log*'
			    20) 'CO Identifier/Keys Zeroized'
			    21) 'KEY NOT INITIALIZED'
			    22) 'DATA NOT ENCRYPTED'
			    23) 'ERROR, KEY INDEX EXPIRED'
			    24) 'Data Encrypted'
			Oid=1.3.6.1.4.1.31968.3.1.4.1.7.84
			"
	::= { txStatusItems 84 }

txTransecKeyIndex OBJECT-TYPE
	SYNTAX		Unsigned32
	UNITS		"1"
	MAX-ACCESS	read-only
	STATUS		current
	DESCRIPTION "Tx Key Index
			Oid=1.3.6.1.4.1.31968.3.1.4.1.7.85
			"
	::= { txStatusItems 85 }

txMccRate OBJECT-TYPE
	SYNTAX		Unsigned32
	UNITS		"1 bps"
	MAX-ACCESS	read-only
	STATUS		current
	DESCRIPTION "Tx MCC Rate
			Oid=1.3.6.1.4.1.31968.3.1.4.1.7.86
			"
	::= { txStatusItems 86 }

txMccAverage OBJECT-TYPE
	SYNTAX		Unsigned32
	UNITS		"1 bps"
	MAX-ACCESS	read-only
	STATUS		current
	DESCRIPTION "Tx Average MCC Rate
			Oid=1.3.6.1.4.1.31968.3.1.4.1.7.87
			"
	::= { txStatusItems 87 }

txAcmRate OBJECT-TYPE
	SYNTAX		Unsigned32
	UNITS		"1 bps"
	MAX-ACCESS	read-only
	STATUS		current
	DESCRIPTION "Tx ACM/AUPC Rate
			Oid=1.3.6.1.4.1.31968.3.1.4.1.7.88
			"
	::= { txStatusItems 88 }

txAcmAverage OBJECT-TYPE
	SYNTAX		Unsigned32
	UNITS		"1 bps"
	MAX-ACCESS	read-only
	STATUS		current
	DESCRIPTION "Tx Average ACM/AUPC Rate
			Oid=1.3.6.1.4.1.31968.3.1.4.1.7.89
			"
	::= { txStatusItems 89 }

txCalStatus OBJECT-TYPE
	SYNTAX		DisplayString
	MAX-ACCESS	read-only
	STATUS		current
	DESCRIPTION "Tx Cal Task Status
			Oid=1.3.6.1.4.1.31968.3.1.4.1.7.91
			"
	::= { txStatusItems 91 }

txDcOffsetCal OBJECT-TYPE
	SYNTAX		DisplayString
	MAX-ACCESS	read-only
	STATUS		current
	DESCRIPTION "Tx DC Offset Cal Status
			Oid=1.3.6.1.4.1.31968.3.1.4.1.7.92
			"
	::= { txStatusItems 92 }

txLevelBalCal OBJECT-TYPE
	SYNTAX		DisplayString
	MAX-ACCESS	read-only
	STATUS		current
	DESCRIPTION "Tx Level Balance Cal Status
			Oid=1.3.6.1.4.1.31968.3.1.4.1.7.93
			"
	::= { txStatusItems 93 }

txPhaseBalCal OBJECT-TYPE
	SYNTAX		DisplayString
	MAX-ACCESS	read-only
	STATUS		current
	DESCRIPTION "Tx Phase Balance Cal Status
			Oid=1.3.6.1.4.1.31968.3.1.4.1.7.94
			"
	::= { txStatusItems 94 }

txDelayBalCal OBJECT-TYPE
	SYNTAX		DisplayString
	MAX-ACCESS	read-only
	STATUS		current
	DESCRIPTION "Tx Delay Balance Cal Status
			Oid=1.3.6.1.4.1.31968.3.1.4.1.7.95
			"
	::= { txStatusItems 95 }

txLevelCal OBJECT-TYPE
	SYNTAX		DisplayString
	MAX-ACCESS	read-only
	STATUS		current
	DESCRIPTION "Tx Level Cal Status
			Oid=1.3.6.1.4.1.31968.3.1.4.1.7.96
			"
	::= { txStatusItems 96 }

txTiltCal OBJECT-TYPE
	SYNTAX		DisplayString
	MAX-ACCESS	read-only
	STATUS		current
	DESCRIPTION "Tx Tilt Cal Status
			Oid=1.3.6.1.4.1.31968.3.1.4.1.7.97
			"
	::= { txStatusItems 97 }

txMemTest OBJECT-TYPE
	SYNTAX		INTEGER {
		pass(0),
		fail(1)
	}
	MAX-ACCESS	read-only
	STATUS		current
	DESCRIPTION "Tx QoS Memory Test, where:
			    0) 'Pass'
			    1) 'FAIL'
			Oid=1.3.6.1.4.1.31968.3.1.4.1.7.98
			"
	::= { txStatusItems 98 }

txRemoteMargin OBJECT-TYPE
	SYNTAX		Integer32
	UNITS		"0.01 dB"
	MAX-ACCESS	read-only
	STATUS		current
	DESCRIPTION "Tx Remote QEF Margin
			Oid=1.3.6.1.4.1.31968.3.1.4.1.7.99
			"
	::= { txStatusItems 99 }

txTrialWaveforms OBJECT-TYPE
	SYNTAX		DisplayString
	MAX-ACCESS	read-only
	STATUS		current
	DESCRIPTION "Tx Trial Waveforms
			Oid=1.3.6.1.4.1.31968.3.1.4.1.7.100
			"
	::= { txStatusItems 100 }

txTrialChannelLimit OBJECT-TYPE
	SYNTAX		Unsigned32
	UNITS		"1"
	MAX-ACCESS	read-only
	STATUS		current
	DESCRIPTION "Tx Trial Channel Limit
			Oid=1.3.6.1.4.1.31968.3.1.4.1.7.101
			"
	::= { txStatusItems 101 }

txTrialModulationLimit OBJECT-TYPE
	SYNTAX		INTEGER {
		n4Ary(0),
		n8Ary(1),
		n16Ary(2),
		n32Ary(3),
		n64Ary(4),
		n128Ary(5),
		n256Ary(6),
		n512Ary(7)
	}
	MAX-ACCESS	read-only
	STATUS		current
	DESCRIPTION "Tx Trial Modulation Limit, where:
			    0) '4-ary'
			    1) '8-ary'
			    2) '16-ary'
			    3) '32-ary'
			    4) '64-ary'
			    5) '128-ary'
			    6) '256-ary'
			    7) '512-ary'
			Oid=1.3.6.1.4.1.31968.3.1.4.1.7.102
			"
	::= { txStatusItems 102 }

txTrialTransec OBJECT-TYPE
	SYNTAX		INTEGER {
		none(0),
		aes128(1),
		aes128Aes192(2),
		aes128Aes192Aes256(3)
	}
	MAX-ACCESS	read-only
	STATUS		current
	DESCRIPTION "Tx Trial TRANSEC, where:
			    0) 'None'
			    1) 'AES-128'
			    2) 'AES-128, AES-192'
			    3) 'AES-128, AES-192, AES-256'
			Oid=1.3.6.1.4.1.31968.3.1.4.1.7.103
			"
	::= { txStatusItems 103 }

txTrialBitRateLimit OBJECT-TYPE
	SYNTAX		Unsigned32
	UNITS		"1 bps"
	MAX-ACCESS	read-only
	STATUS		current
	DESCRIPTION "Tx Trial Bit Rate Limit
			Oid=1.3.6.1.4.1.31968.3.1.4.1.7.104
			"
	::= { txStatusItems 104 }

txTrialSymbolRateLimit OBJECT-TYPE
	SYNTAX		Unsigned32
	UNITS		"1 sps"
	MAX-ACCESS	read-only
	STATUS		current
	DESCRIPTION "Tx Trial Symbol Rate Limit
			Oid=1.3.6.1.4.1.31968.3.1.4.1.7.105
			"
	::= { txStatusItems 105 }

txTrialSmartCarrierBitRateLimit OBJECT-TYPE
	SYNTAX		Unsigned32
	UNITS		"1 bps"
	MAX-ACCESS	read-only
	STATUS		current
	DESCRIPTION "Tx Trial Smart Cxr Bit Rate Limit
			Oid=1.3.6.1.4.1.31968.3.1.4.1.7.106
			"
	::= { txStatusItems 106 }

txTrialSmartCarrierSymbolRateLimit OBJECT-TYPE
	SYNTAX		Unsigned32
	UNITS		"1 sps"
	MAX-ACCESS	read-only
	STATUS		current
	DESCRIPTION "Tx Trial Smart Cxr Symbol Rate Limit
			Oid=1.3.6.1.4.1.31968.3.1.4.1.7.107
			"
	::= { txStatusItems 107 }

txRemoteSnr OBJECT-TYPE
	SYNTAX		Integer32
	UNITS		"0.01 dB"
	MAX-ACCESS	read-only
	STATUS		current
	DESCRIPTION "Tx Remote SNR
			Oid=1.3.6.1.4.1.31968.3.1.4.1.7.108
			"
	::= { txStatusItems 108 }

txDsssSymbolRate OBJECT-TYPE
	SYNTAX		Unsigned32
	UNITS		"1 sps"
	MAX-ACCESS	read-only
	STATUS		current
	DESCRIPTION "Tx Despread Symbol Rate
			Oid=1.3.6.1.4.1.31968.3.1.4.1.7.109
			"
	::= { txStatusItems 109 }

txDsssModcod OBJECT-TYPE
	SYNTAX		INTEGER {
		bpsk1x2(0),
		bpsk8x15(1),
		bpsk4x7(2),
		bpsk8x13(3),
		bpsk2x3(4),
		bpsk16x23(5),
		bpsk8x11(6),
		bpsk16x21(7),
		bpsk4x5(8),
		bpsk16x19(9),
		bpsk8x9(10)
	}
	MAX-ACCESS	read-only
	STATUS		current
	DESCRIPTION "Tx ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'BPSK 16/21'
			    8) 'BPSK 4/5'
			    9) 'BPSK 16/19'
			    10) 'BPSK 8/9'
			Oid=1.3.6.1.4.1.31968.3.1.4.1.7.110
			"
	::= { txStatusItems 110 }

txVcmAvailableCir OBJECT-TYPE
	SYNTAX		Integer32
	MAX-ACCESS	read-only
	STATUS		current
	DESCRIPTION "Tx Total Available CIR
			Oid=1.3.6.1.4.1.31968.3.1.4.1.7.111
			"
	::= { txStatusItems 111 }

txVcmTotalCir OBJECT-TYPE
	SYNTAX		Unsigned32
	UNITS		"1 bps"
	MAX-ACCESS	read-only
	STATUS		current
	DESCRIPTION "Tx Total Desired CIR
			Oid=1.3.6.1.4.1.31968.3.1.4.1.7.112
			"
	::= { txStatusItems 112 }

txVcmDrainMinModcod OBJECT-TYPE
	SYNTAX		Unsigned32
	UNITS		"0.01 ms"
	MAX-ACCESS	read-only
	STATUS		current
	DESCRIPTION "Tx Drain Time @ Min ModCods
			Oid=1.3.6.1.4.1.31968.3.1.4.1.7.113
			"
	::= { txStatusItems 113 }

txVcmCirMinModcod OBJECT-TYPE
	SYNTAX		Unsigned32
	UNITS		"1 bps"
	MAX-ACCESS	read-only
	STATUS		current
	DESCRIPTION "Tx Total CIR @ Min ModCods
			Oid=1.3.6.1.4.1.31968.3.1.4.1.7.114
			"
	::= { txStatusItems 114 }

txVcmBinaryStatus OBJECT-TYPE
	SYNTAX		BITS {
		almCirLmt(0),
		spare0(1),
		spare1(2),
		spare2(3),
		spare3(4),
		spare4(5),
		spare5(6),
		spare6(7),
		spare7(8),
		spare8(9),
		spare9(10),
		spare10(11),
		spare11(12),
		spare12(13),
		spare13(14),
		spare14(15),
		almMcc1(16),
		almMcc2(17),
		almMcc3(18),
		almMcc4(19),
		almMcc5(20),
		almMcc6(21),
		almMcc7(22),
		almMcc8(23),
		almMcc9(24),
		almMcc10(25),
		almMcc11(26),
		almMcc12(27),
		almMcc13(28),
		almMcc14(29),
		almMcc15(30),
		almMcc16(31),
		almMin1(32),
		almMin2(33),
		almMin3(34),
		almMin4(35),
		almMin5(36),
		almMin6(37),
		almMin7(38),
		almMin8(39),
		almMin9(40),
		almMin10(41),
		almMin11(42),
		almMin12(43),
		almMin13(44),
		almMin14(45),
		almMin15(46),
		almMin16(47),
		almEsn01(48),
		almEsn02(49),
		almEsn03(50),
		almEsn04(51),
		almEsn05(52),
		almEsn06(53),
		almEsn07(54),
		almEsn08(55),
		almEsn09(56),
		almEsn010(57),
		almEsn011(58),
		almEsn012(59),
		almEsn013(60),
		almEsn014(61),
		almEsn015(62),
		almEsn016(63),
		almData1(64),
		almData2(65),
		almData3(66),
		almData4(67),
		almData5(68),
		almData6(69),
		almData7(70),
		almData8(71),
		almData9(72),
		almData10(73),
		almData11(74),
		almData12(75),
		almData13(76),
		almData14(77),
		almData15(78),
		almData16(79)
	}
	MAX-ACCESS	read-only
	STATUS		current
	DESCRIPTION "Tx Binary VCM Status, where:
			    0) 'Alm CIR Lmt'
			    1) 'Spare0'
			    2) 'Spare1'
			    3) 'Spare2'
			    4) 'Spare3'
			    5) 'Spare4'
			    6) 'Spare5'
			    7) 'Spare6'
			    8) 'Spare7'
			    9) 'Spare8'
			    10) 'Spare9'
			    11) 'Spare10'
			    12) 'Spare11'
			    13) 'Spare12'
			    14) 'Spare13'
			    15) 'Spare14'
			    16) 'Alm MCC 1'
			    17) 'Alm MCC 2'
			    18) 'Alm MCC 3'
			    19) 'Alm MCC 4'
			    20) 'Alm MCC 5'
			    21) 'Alm MCC 6'
			    22) 'Alm MCC 7'
			    23) 'Alm MCC 8'
			    24) 'Alm MCC 9'
			    25) 'Alm MCC 10'
			    26) 'Alm MCC 11'
			    27) 'Alm MCC 12'
			    28) 'Alm MCC 13'
			    29) 'Alm MCC 14'
			    30) 'Alm MCC 15'
			    31) 'Alm MCC 16'
			    32) 'Alm Min 1'
			    33) 'Alm Min 2'
			    34) 'Alm Min 3'
			    35) 'Alm Min 4'
			    36) 'Alm Min 5'
			    37) 'Alm Min 6'
			    38) 'Alm Min 7'
			    39) 'Alm Min 8'
			    40) 'Alm Min 9'
			    41) 'Alm Min 10'
			    42) 'Alm Min 11'
			    43) 'Alm Min 12'
			    44) 'Alm Min 13'
			    45) 'Alm Min 14'
			    46) 'Alm Min 15'
			    47) 'Alm Min 16'
			    48) 'Alm EsN0 1'
			    49) 'Alm EsN0 2'
			    50) 'Alm EsN0 3'
			    51) 'Alm EsN0 4'
			    52) 'Alm EsN0 5'
			    53) 'Alm EsN0 6'
			    54) 'Alm EsN0 7'
			    55) 'Alm EsN0 8'
			    56) 'Alm EsN0 9'
			    57) 'Alm EsN0 10'
			    58) 'Alm EsN0 11'
			    59) 'Alm EsN0 12'
			    60) 'Alm EsN0 13'
			    61) 'Alm EsN0 14'
			    62) 'Alm EsN0 15'
			    63) 'Alm EsN0 16'
			    64) 'Alm Data 1'
			    65) 'Alm Data 2'
			    66) 'Alm Data 3'
			    67) 'Alm Data 4'
			    68) 'Alm Data 5'
			    69) 'Alm Data 6'
			    70) 'Alm Data 7'
			    71) 'Alm Data 8'
			    72) 'Alm Data 9'
			    73) 'Alm Data 10'
			    74) 'Alm Data 11'
			    75) 'Alm Data 12'
			    76) 'Alm Data 13'
			    77) 'Alm Data 14'
			    78) 'Alm Data 15'
			    79) 'Alm Data 16'
			Oid=1.3.6.1.4.1.31968.3.1.4.1.7.115
			"
	::= { txStatusItems 115 }

txHdrModcod OBJECT-TYPE
	SYNTAX		INTEGER {
		fr80t5x4L8(0),
		fr80t5x4L7(1),
		fr80t5x4L6(2),
		fr80t5x4L5(3),
		fr80t5x4L4(4),
		fr80t5x4L3(5),
		fr80t5x4L2(6),
		fr80t5x4L1(7),
		fr80t5x16L3(8),
		fr80t5x16L2(9),
		fr80t5x16L1(10),
		fr80t5x16R(11),
		fr80t5x16H1(12),
		fr80t5x16H2(13),
		fr80t5x16H3(14),
		fr80t5x16H4(15),
		fr80t5x16H5(16),
		fr80t5x16H6(17),
		fr80t5x32H1(18),
		fr80t5x32H2(19),
		fr80t5x32H3(20),
		fr80t5x32H4(21),
		fr80t5x32H5(22),
		fr80t5x32H6(23),
		fr80t5x64R(24),
		fr80t5x64H1(25),
		fr80t5x64H2(26),
		fr80t5x64H3(27),
		fr80t5x64H4(28),
		fr80t5x64H5(29),
		fr80t5x64H6(30)
	}
	MAX-ACCESS	read-only
	STATUS		current
	DESCRIPTION "Tx ModCod, where:
			    0) 'FR80T5X4-L8'
			    1) 'FR80T5X4-L7'
			    2) 'FR80T5X4-L6'
			    3) 'FR80T5X4-L5'
			    4) 'FR80T5X4-L4'
			    5) 'FR80T5X4-L3'
			    6) 'FR80T5X4-L2'
			    7) 'FR80T5X4-L1'
			    8) 'FR80T5X16-L3'
			    9) 'FR80T5X16-L2'
			    10) 'FR80T5X16-L1'
			    11) 'FR80T5X16-R'
			    12) 'FR80T5X16-H1'
			    13) 'FR80T5X16-H2'
			    14) 'FR80T5X16-H3'
			    15) 'FR80T5X16-H4'
			    16) 'FR80T5X16-H5'
			    17) 'FR80T5X16-H6'
			    18) 'FR80T5X32-H1'
			    19) 'FR80T5X32-H2'
			    20) 'FR80T5X32-H3'
			    21) 'FR80T5X32-H4'
			    22) 'FR80T5X32-H5'
			    23) 'FR80T5X32-H6'
			    24) 'FR80T5X64-R'
			    25) 'FR80T5X64-H1'
			    26) 'FR80T5X64-H2'
			    27) 'FR80T5X64-H3'
			    28) 'FR80T5X64-H4'
			    29) 'FR80T5X64-H5'
			    30) 'FR80T5X64-H6'
			Oid=1.3.6.1.4.1.31968.3.1.4.1.7.116
			"
	::= { txStatusItems 116 }

txFramePeriod OBJECT-TYPE
	SYNTAX		Unsigned32
	UNITS		"0.01 ms"
	MAX-ACCESS	read-only
	STATUS		current
	DESCRIPTION "Tx Frame Period
			Oid=1.3.6.1.4.1.31968.3.1.4.1.7.117
			"
	::= { txStatusItems 117 }

txStatusTable OBJECT-TYPE
	SYNTAX		SEQUENCE OF TxStatusEntry
	MAX-ACCESS	not-accessible
	STATUS		current
	DESCRIPTION "Tx Status Channel Table
			Oid=1.3.6.1.4.1.31968.3.1.4.1.8
			"
	::= { m7xcModemObjs 8 }

txStatusEntry OBJECT-TYPE
	SYNTAX		TxStatusEntry
	MAX-ACCESS	not-accessible
	STATUS		current
	DESCRIPTION "Tx Status Channel Entry
			Oid=1.3.6.1.4.1.31968.3.1.4.1.8.1
			"
	INDEX {
		txStatusIndex
	}
	::= { txStatusTable 1 }

TxStatusEntry ::=
	SEQUENCE {
		txStatusIndex           Unsigned32,
		txTableStatus           INTEGER,
		txOccupied              Unsigned32,
		txVcmStatus             INTEGER,
		txVcmModcod             INTEGER,
		txVcmMargin             Integer32,
		txVcmEsn0               Integer32,
		txVcmQueueAverage       Unsigned32,
		txVcmQueueRate          Unsigned32,
		txVcmQueuePackets       DisplayString,
		txVcmQueueBytes         DisplayString,
		txVcmQueueDropped       DisplayString,
		txVcmQueueFull          DisplayString
	}

txStatusIndex OBJECT-TYPE
	SYNTAX		Unsigned32(1..16)
	MAX-ACCESS	not-accessible
	STATUS		current
	DESCRIPTION "Tx Status Channel Index
			Oid=1.3.6.1.4.1.31968.3.1.4.1.8.1.1
			"
	::= { txStatusEntry 1 }

txTableStatus OBJECT-TYPE
	SYNTAX		INTEGER {
		placeholder(0)
	}
	MAX-ACCESS	read-only
	STATUS		current
	DESCRIPTION "Tx Status Table, where:
			    0) 'PlaceHolder'
			Oid=1.3.6.1.4.1.31968.3.1.4.1.8.1.2
			"
	::= { txStatusEntry 2 }

txOccupied OBJECT-TYPE
	SYNTAX		Unsigned32
	UNITS		"1 Hz"
	MAX-ACCESS	read-only
	STATUS		current
	DESCRIPTION "Tx Occupied Bandwidth
			Oid=1.3.6.1.4.1.31968.3.1.4.1.8.1.3
			"
	::= { txStatusEntry 3 }

txVcmStatus OBJECT-TYPE
	SYNTAX		INTEGER {
		sendingOk(0),
		sendingOcxoWarming(1),
		sendingDataInactivityAlarm(50),
		sendingQueueLowEsN0Alarm(51),
		sendingQueueMinModcodAlarm(52),
		sendingQueueRemoteChanAlarm(53),
		sendingCirLimitAlarm(54),
		sendingAupcLimitAlarm(55),
		sendingAcuAlarm(56),
		sendingRefAlarm(57),
		sendingDataPortAlarm(58),
		sendingTestActive(59),
		sendingTransecAlarm(60),
		sendingDataInactivityAlarm(100),
		sendingQueueLowEsN0Alarm(101),
		sendingQueueMinModcodAlarm(102),
		sendingQueueRemoteChanAlarm(103),
		sendingCirLimitAlarm(104),
		sendingAupcLimitAlarm(105),
		sendingAcuAlarm(106),
		sendingRefAlarm(107),
		sendingDataPortAlarm(108),
		sendingTestActive(109),
		sendingTransecAlarm(110),
		offlineOk(150),
		offlineOcxoWarming(151),
		offlineDataInactivityAlarm(152),
		offlineQueueLowEsN0Alarm(153),
		offlineQueueMinModcodAlarm(154),
		offlineQueueRemoteChanAlarm(155),
		offlineCirLimitAlarm(156),
		offlineAupcLimitAlarm(157),
		offlineAcuAlarm(158),
		offlineRefAlarm(159),
		offlineDataPortAlarm(160),
		offlineTestActive(161),
		offlineTransecAlarm(162),
		offlineOcxoWarming(200),
		offlineDataInactivityAlarm(201),
		offlineQueueLowEsN0Alarm(202),
		offlineQueueMinModcodAlarm(203),
		offlineQueueRemoteChanAlarm(204),
		offlineCirLimitAlarm(205),
		offlineAupcLimitAlarm(206),
		offlineAcuAlarm(207),
		offlineRefAlarm(208),
		offlineDataPortAlarm(209),
		offlineTestActive(210),
		offlineTransecAlarm(211),
		standbyOcxoWarming(250),
		standbyMonitorAlarm(251),
		standbyRxMuteRequest(252),
		standbyDataInactivityAlarm(253),
		standbyAcuAlarm(254),
		standbyMgmtPortAlarm(255),
		standbyDataPortAlarm(256),
		standbyRefAlarm(257),
		standbyTransecAlarm(258),
		standbyPowerInputAlarm(259),
		txMutedOcxoWarming(300),
		txMutedMonitorAlarm(301),
		txMutedRxMuteRequest(302),
		txMutedDataInactivityAlarm(303),
		txMutedAcuAlarm(304),
		txMutedMgmtPortAlarm(305),
		txMutedDataPortAlarm(306),
		txMutedRefAlarm(307),
		txMutedTransecAlarm(308),
		standbyPowerInputAlarm(309),
		txOutputOff(350),
		queueOff(351),
		fipsAlarm(352),
		hardwareAlarm(353),
		invalidKey(355),
		loadFailed(356),
		overTemperature(357),
		overTemperatureShutdown(358)
	}
	MAX-ACCESS	read-only
	STATUS		current
	DESCRIPTION "Tx Queue Status, where:
			    0) 'Sending, Ok'
			    1) 'Sending, OCXO Warming...'
			    50) 'Sending, Data Inactivity Alarm'
			    51) 'Sending, Queue Low Es/N0 Alarm'
			    52) 'Sending, Queue Min Modcod Alarm'
			    53) 'Sending, Queue Remote Chan Alarm'
			    54) 'Sending, CIR Limit Alarm'
			    55) 'Sending, AUPC Limit Alarm'
			    56) 'Sending, ACU Alarm'
			    57) 'Sending, Ref Alarm'
			    58) 'Sending, Data Port Alarm'
			    59) 'Sending, Test Active'
			    60) 'Sending, TRANSEC Alarm'
			    100) 'Sending, DATA INACTIVITY ALARM'
			    101) 'Sending, QUEUE LOW Es/N0 ALARM'
			    102) 'Sending, QUEUE MIN MODCOD ALARM'
			    103) 'Sending, QUEUE REMOTE CHAN ALARM'
			    104) 'Sending, CIR LIMIT ALARM'
			    105) 'Sending, AUPC LIMIT ALARM'
			    106) 'Sending, ACU ALARM'
			    107) 'Sending, REF ALARM'
			    108) 'Sending, DATA PORT ALARM'
			    109) 'Sending, TEST ACTIVE'
			    110) 'Sending, TRANSEC ALARM'
			    150) 'Offline, Ok'
			    151) 'Offline, OCXO Warming...'
			    152) 'Offline, Data Inactivity Alarm'
			    153) 'Offline, Queue Low Es/N0 Alarm'
			    154) 'Offline, Queue Min ModCod Alarm'
			    155) 'Offline, Queue Remote Chan Alarm'
			    156) 'Offline, CIR Limit Alarm'
			    157) 'Offline, AUPC Limit Alarm'
			    158) 'Offline, ACU Alarm'
			    159) 'Offline, Ref Alarm'
			    160) 'Offline, Data Port Alarm'
			    161) 'Offline, Test Active'
			    162) 'Offline, TRANSEC Alarm'
			    200) 'Offline, OCXO WARMING...'
			    201) 'Offline, DATA INACTIVITY ALARM'
			    202) 'Offline, QUEUE LOW Es/N0 ALARM'
			    203) 'Offline, QUEUE Min ModCod ALARM'
			    204) 'Offline, QUEUE REMOTE CHAN ALARM'
			    205) 'Offline, CIR LIMIT ALARM'
			    206) 'Offline, AUPC LIMIT ALARM'
			    207) 'Offline, ACU ALARM'
			    208) 'Offline, REF ALARM'
			    209) 'Offline, DATA PORT ALARM'
			    210) 'Offline, TEST ACTIVE'
			    211) 'Offline, TRANSEC ALARM'
			    250) 'Standby, OCXO Warming...'
			    251) 'Standby, Monitor Alarm'
			    252) 'Standby, Rx Mute Request'
			    253) 'Standby, Data Inactivity Alarm'
			    254) 'Standby, ACU Alarm'
			    255) 'Standby, Mgmt Port Alarm'
			    256) 'Standby, Data Port Alarm'
			    257) 'Standby, Ref Alarm'
			    258) 'Standby, TRANSEC Alarm'
			    259) 'Standby, Power Input Alarm'
			    300) 'Tx MUTED, OCXO WARMING...'
			    301) 'Tx MUTED, MONITOR ALARM'
			    302) 'Tx MUTED, Rx MUTE REQUEST'
			    303) 'Tx MUTED, DATA INACTIVITY ALARM'
			    304) 'Tx MUTED, ACU ALARM'
			    305) 'Tx MUTED, Mgmt PORT ALARM'
			    306) 'Tx MUTED, DATA PORT ALARM'
			    307) 'Tx MUTED, REF ALARM'
			    308) 'Tx MUTED, TRANSEC ALARM'
			    309) 'Standby, POWER INPUT ALARM'
			    350) 'Tx OUTPUT OFF'
			    351) 'Queue Off'
			    352) 'FIPS ALARM'
			    353) 'HARDWARE ALARM'
			    355) 'INVALID KEY'
			    356) 'LOAD FAILED'
			    357) 'OVER TEMPERATURE'
			    358) 'OVER TEMPERATURE SHUTDOWN'
			Oid=1.3.6.1.4.1.31968.3.1.4.1.8.1.4
			"
	::= { txStatusEntry 4 }

txVcmModcod OBJECT-TYPE
	SYNTAX		INTEGER {
		qpsk1x4Normal(0),
		qpsk1x4NormalWithPilot(1),
		qpsk13x45Normal(2),
		qpsk13x45NormalWithPilot(3),
		qpsk1x3Normal(4),
		qpsk1x3NormalWithPilot(5),
		qpsk2x5Normal(6),
		qpsk2x5NormalWithPilot(7),
		qpsk9x20Normal(8),
		qpsk9x20NormalWithPilot(9),
		qpsk1x2Normal(10),
		qpsk1x2NormalWithPilot(11),
		qpsk11x20Normal(12),
		qpsk11x20NormalWithPilot(13),
		qpsk3x5Normal(14),
		qpsk3x5NormalWithPilot(15),
		qpsk2x3Normal(16),
		qpsk2x3NormalWithPilot(17),
		qpsk3x4Normal(18),
		qpsk3x4NormalWithPilot(19),
		qpsk4x5Normal(20),
		qpsk4x5NormalWithPilot(21),
		qpsk5x6Normal(22),
		qpsk5x6NormalWithPilot(23),
		qpsk8x9Normal(24),
		qpsk8x9NormalWithPilot(25),
		qpsk9x10Normal(26),
		qpsk9x10NormalWithPilot(27),
		n8apsk5x9LNormal(28),
		n8apsk5x9LNormalWithPilot(29),
		n8apsk26x45LNormal(30),
		n8apsk26x45LNormalWithPilot(31),
		n8psk3x5NormalWithPilot(32),
		n8psk23x36Normal(33),
		n8psk23x36NormalWithPilot(34),
		n8psk2x3NormalWithPilot(35),
		n8psk25x36Normal(36),
		n8psk25x36NormalWithPilot(37),
		n8psk13x18Normal(38),
		n8psk13x18NormalWithPilot(39),
		n8psk3x4Normal(40),
		n8psk3x4NormalWithPilot(41),
		n8psk5x6Normal(42),
		n8psk5x6NormalWithPilot(43),
		n8psk8x9Normal(44),
		n8psk8x9NormalWithPilot(45),
		n8psk9x10Normal(46),
		n8psk9x10NormalWithPilot(47),
		n16apsk1x2LNormal(48),
		n16apsk1x2LNormalWithPilot(49),
		n16apsk8x15LNormal(50),
		n16apsk8x15LNormalWithPilot(51),
		n16apsk5x9LNormal(52),
		n16apsk5x9LNormalWithPilot(53),
		n16apsk26x45Normal(54),
		n16apsk26x45NormalWithPilot(55),
		n16apsk3x5Normal(56),
		n16apsk3x5NormalWithPilot(57),
		n16apsk3x5LNormal(58),
		n16apsk3x5LNormalWithPilot(59),
		n16apsk28x45Normal(60),
		n16apsk28x45NormalWithPilot(61),
		n16apsk23x36Normal(62),
		n16apsk23x36NormalWithPilot(63),
		n16apsk2x3LNormal(64),
		n16apsk2x3LNormalWithPilot(65),
		n16apsk2x3Normal(66),
		n16apsk2x3NormalWithPilot(67),
		n16apsk25x36Normal(68),
		n16apsk25x36NormalWithPilot(69),
		n16apsk13x18Normal(70),
		n16apsk13x18NormalWithPilot(71),
		n16apsk3x4NormalWithPilot(72),
		n16apsk7x9Normal(73),
		n16apsk7x9NormalWithPilot(74),
		n16apsk4x5Normal(75),
		n16apsk4x5NormalWithPilot(76),
		n16apsk5x6Normal(77),
		n16apsk5x6NormalWithPilot(78),
		n16apsk77x90Normal(79),
		n16apsk77x90NormalWithPilot(80),
		n16apsk8x9Normal(81),
		n16apsk8x9NormalWithPilot(82),
		n16apsk9x10Normal(83),
		n16apsk9x10NormalWithPilot(84),
		n32apsk2x3LNormal(85),
		n32apsk2x3LNormalWithPilot(86),
		n32apsk32x45Normal(87),
		n32apsk32x45NormalWithPilot(88),
		n32apsk11x15Normal(89),
		n32apsk11x15NormalWithPilot(90),
		n32apsk3x4Normal(91),
		n32apsk3x4NormalWithPilot(92),
		n32apsk7x9Normal(93),
		n32apsk7x9NormalWithPilot(94),
		n32apsk4x5NormalWithPilot(95),
		n32apsk5x6Normal(96),
		n32apsk5x6NormalWithPilot(97),
		n32apsk8x9Normal(98),
		n32apsk8x9NormalWithPilot(99),
		n32apsk9x10Normal(100),
		n32apsk9x10NormalWithPilot(101),
		n64apsk32x45LNormal(102),
		n64apsk32x45LNormalWithPilot(103),
		n64apsk11x15Normal(104),
		n64apsk11x15NormalWithPilot(105),
		n64apsk7x9Normal(106),
		n64apsk7x9NormalWithPilot(107),
		n64apsk4x5Normal(108),
		n64apsk4x5NormalWithPilot(109),
		n64apsk5x6Normal(110),
		n64apsk5x6NormalWithPilot(111),
		n128apsk3x4Normal(112),
		n128apsk3x4NormalWithPilot(113),
		n128apsk7x9Normal(114),
		n128apsk7x9NormalWithPilot(115),
		n256apsk29x45LNormal(116),
		n256apsk29x45LNormalWithPilot(117),
		n256apsk2x3LNormal(118),
		n256apsk2x3LNormalWithPilot(119),
		n256apsk31x45LNormal(120),
		n256apsk31x45LNormalWithPilot(121),
		n256apsk32x45Normal(122),
		n256apsk32x45NormalWithPilot(123),
		n256apsk11x15LNormal(124),
		n256apsk11x15LNormalWithPilot(125),
		n256apsk3x4Normal(126),
		n256apsk3x4NormalWithPilot(127),
		qpsk1x4Short(128),
		qpsk1x4ShortWithPilot(129),
		qpsk11x45Short(130),
		qpsk11x45ShortWithPilot(131),
		qpsk4x15Short(132),
		qpsk4x15ShortWithPilot(133),
		qpsk14x45Short(134),
		qpsk14x45ShortWithPilot(135),
		qpsk1x3Short(136),
		qpsk1x3ShortWithPilot(137),
		qpsk2x5Short(138),
		qpsk2x5ShortWithPilot(139),
		qpsk1x2Short(140),
		qpsk1x2ShortWithPilot(141),
		qpsk7x15Short(142),
		qpsk7x15ShortWithPilot(143),
		qpsk8x15Short(144),
		qpsk8x15ShortWithPilot(145),
		qpsk3x5Short(146),
		qpsk3x5ShortWithPilot(147),
		qpsk2x3Short(148),
		qpsk2x3ShortWithPilot(149),
		qpsk32x45Short(150),
		qpsk32x45ShortWithPilot(151),
		qpsk3x4Short(152),
		qpsk3x4ShortWithPilot(153),
		qpsk4x5Short(154),
		qpsk4x5ShortWithPilot(155),
		qpsk5x6Short(156),
		qpsk5x6ShortWithPilot(157),
		qpsk8x9Short(158),
		qpsk8x9ShortWithPilot(159),
		n8psk7x15Short(160),
		n8psk7x15ShortWithPilot(161),
		n8psk8x15Short(162),
		n8psk8x15ShortWithPilot(163),
		n8psk26x45Short(164),
		n8psk26x45ShortWithPilot(165),
		n8psk3x5ShortWithPilot(166),
		n8psk2x3ShortWithPilot(167),
		n8psk32x45Short(168),
		n8psk32x45ShortWithPilot(169),
		n8psk3x4Short(170),
		n8psk3x4ShortWithPilot(171),
		n8psk5x6Short(172),
		n8psk5x6ShortWithPilot(173),
		n8psk8x9Short(174),
		n8psk8x9ShortWithPilot(175),
		n16apsk7x15Short(176),
		n16apsk7x15ShortWithPilot(177),
		n16apsk8x15Short(178),
		n16apsk8x15ShortWithPilot(179),
		n16apsk26x45Short(180),
		n16apsk26x45ShortWithPilot(181),
		n16apsk3x5Short(182),
		n16apsk3x5ShortWithPilot(183),
		n16apsk2x3Short(184),
		n16apsk2x3ShortWithPilot(185),
		n16apsk32x45Short(186),
		n16apsk32x45ShortWithPilot(187)
	}
	MAX-ACCESS	read-only
	STATUS		current
	DESCRIPTION "Tx Queue ModCod, where:
			    0) 'QPSK 1/4 Normal'
			    1) 'QPSK 1/4 Normal with Pilot'
			    2) 'QPSK 13/45 Normal'
			    3) 'QPSK 13/45 Normal with Pilot'
			    4) 'QPSK 1/3 Normal'
			    5) 'QPSK 1/3 Normal with Pilot'
			    6) 'QPSK 2/5 Normal'
			    7) 'QPSK 2/5 Normal with Pilot'
			    8) 'QPSK 9/20 Normal'
			    9) 'QPSK 9/20 Normal with Pilot'
			    10) 'QPSK 1/2 Normal'
			    11) 'QPSK 1/2 Normal with Pilot'
			    12) 'QPSK 11/20 Normal'
			    13) 'QPSK 11/20 Normal with Pilot'
			    14) 'QPSK 3/5 Normal'
			    15) 'QPSK 3/5 Normal with Pilot'
			    16) 'QPSK 2/3 Normal'
			    17) 'QPSK 2/3 Normal with Pilot'
			    18) 'QPSK 3/4 Normal'
			    19) 'QPSK 3/4 Normal with Pilot'
			    20) 'QPSK 4/5 Normal'
			    21) 'QPSK 4/5 Normal with Pilot'
			    22) 'QPSK 5/6 Normal'
			    23) 'QPSK 5/6 Normal with Pilot'
			    24) 'QPSK 8/9 Normal'
			    25) 'QPSK 8/9 Normal with Pilot'
			    26) 'QPSK 9/10 Normal'
			    27) 'QPSK 9/10 Normal with Pilot'
			    28) '8APSK 5/9-L Normal'
			    29) '8APSK 5/9-L Normal with Pilot'
			    30) '8APSK 26/45-L Normal'
			    31) '8APSK 26/45-L Normal with Pilot'
			    32) '8PSK 3/5 Normal with Pilot'
			    33) '8PSK 23/36 Normal'
			    34) '8PSK 23/36 Normal with Pilot'
			    35) '8PSK 2/3 Normal with Pilot'
			    36) '8PSK 25/36 Normal'
			    37) '8PSK 25/36 Normal with Pilot'
			    38) '8PSK 13/18 Normal'
			    39) '8PSK 13/18 Normal with Pilot'
			    40) '8PSK 3/4 Normal'
			    41) '8PSK 3/4 Normal with Pilot'
			    42) '8PSK 5/6 Normal'
			    43) '8PSK 5/6 Normal with Pilot'
			    44) '8PSK 8/9 Normal'
			    45) '8PSK 8/9 Normal with Pilot'
			    46) '8PSK 9/10 Normal'
			    47) '8PSK 9/10 Normal with Pilot'
			    48) '16APSK 1/2-L Normal'
			    49) '16APSK 1/2-L Normal with Pilot'
			    50) '16APSK 8/15-L Normal'
			    51) '16APSK 8/15-L Normal with Pilot'
			    52) '16APSK 5/9-L Normal'
			    53) '16APSK 5/9-L Normal with Pilot'
			    54) '16APSK 26/45 Normal'
			    55) '16APSK 26/45 Normal with Pilot'
			    56) '16APSK 3/5 Normal'
			    57) '16APSK 3/5 Normal with Pilot'
			    58) '16APSK 3/5-L Normal'
			    59) '16APSK 3/5-L Normal with Pilot'
			    60) '16APSK 28/45 Normal'
			    61) '16APSK 28/45 Normal with Pilot'
			    62) '16APSK 23/36 Normal'
			    63) '16APSK 23/36 Normal with Pilot'
			    64) '16APSK 2/3-L Normal'
			    65) '16APSK 2/3-L Normal with Pilot'
			    66) '16APSK 2/3 Normal'
			    67) '16APSK 2/3 Normal with Pilot'
			    68) '16APSK 25/36 Normal'
			    69) '16APSK 25/36 Normal with Pilot'
			    70) '16APSK 13/18 Normal'
			    71) '16APSK 13/18 Normal with Pilot'
			    72) '16APSK 3/4 Normal with Pilot'
			    73) '16APSK 7/9 Normal'
			    74) '16APSK 7/9 Normal with Pilot'
			    75) '16APSK 4/5 Normal'
			    76) '16APSK 4/5 Normal with Pilot'
			    77) '16APSK 5/6 Normal'
			    78) '16APSK 5/6 Normal with Pilot'
			    79) '16APSK 77/90 Normal'
			    80) '16APSK 77/90 Normal with Pilot'
			    81) '16APSK 8/9 Normal'
			    82) '16APSK 8/9 Normal with Pilot'
			    83) '16APSK 9/10 Normal'
			    84) '16APSK 9/10 Normal with Pilot'
			    85) '32APSK 2/3-L Normal'
			    86) '32APSK 2/3-L Normal with Pilot'
			    87) '32APSK 32/45 Normal'
			    88) '32APSK 32/45 Normal with Pilot'
			    89) '32APSK 11/15 Normal'
			    90) '32APSK 11/15 Normal with Pilot'
			    91) '32APSK 3/4 Normal'
			    92) '32APSK 3/4 Normal with Pilot'
			    93) '32APSK 7/9 Normal'
			    94) '32APSK 7/9 Normal with Pilot'
			    95) '32APSK 4/5 Normal with Pilot'
			    96) '32APSK 5/6 Normal'
			    97) '32APSK 5/6 Normal with Pilot'
			    98) '32APSK 8/9 Normal'
			    99) '32APSK 8/9 Normal with Pilot'
			    100) '32APSK 9/10 Normal'
			    101) '32APSK 9/10 Normal with Pilot'
			    102) '64APSK 32/45-L Normal'
			    103) '64APSK 32/45-L Normal with Pilot'
			    104) '64APSK 11/15 Normal'
			    105) '64APSK 11/15 Normal with Pilot'
			    106) '64APSK 7/9 Normal'
			    107) '64APSK 7/9 Normal with Pilot'
			    108) '64APSK 4/5 Normal'
			    109) '64APSK 4/5 Normal with Pilot'
			    110) '64APSK 5/6 Normal'
			    111) '64APSK 5/6 Normal with Pilot'
			    112) '128APSK 3/4 Normal'
			    113) '128APSK 3/4 Normal with Pilot'
			    114) '128APSK 7/9 Normal'
			    115) '128APSK 7/9 Normal with Pilot'
			    116) '256APSK 29/45-L Normal'
			    117) '256APSK 29/45-L Normal with Pilot'
			    118) '256APSK 2/3-L Normal'
			    119) '256APSK 2/3-L Normal with Pilot'
			    120) '256APSK 31/45-L Normal'
			    121) '256APSK 31/45-L Normal with Pilot'
			    122) '256APSK 32/45 Normal'
			    123) '256APSK 32/45 Normal with Pilot'
			    124) '256APSK 11/15-L Normal'
			    125) '256APSK 11/15-L Normal with Pilot'
			    126) '256APSK 3/4 Normal'
			    127) '256APSK 3/4 Normal with Pilot'
			    128) 'QPSK 1/4 Short'
			    129) 'QPSK 1/4 Short with Pilot'
			    130) 'QPSK 11/45 Short'
			    131) 'QPSK 11/45 Short with Pilot'
			    132) 'QPSK 4/15 Short'
			    133) 'QPSK 4/15 Short with Pilot'
			    134) 'QPSK 14/45 Short'
			    135) 'QPSK 14/45 Short with Pilot'
			    136) 'QPSK 1/3 Short'
			    137) 'QPSK 1/3 Short with Pilot'
			    138) 'QPSK 2/5 Short'
			    139) 'QPSK 2/5 Short with Pilot'
			    140) 'QPSK 1/2 Short'
			    141) 'QPSK 1/2 Short with Pilot'
			    142) 'QPSK 7/15 Short'
			    143) 'QPSK 7/15 Short with Pilot'
			    144) 'QPSK 8/15 Short'
			    145) 'QPSK 8/15 Short with Pilot'
			    146) 'QPSK 3/5 Short'
			    147) 'QPSK 3/5 Short with Pilot'
			    148) 'QPSK 2/3 Short'
			    149) 'QPSK 2/3 Short with Pilot'
			    150) 'QPSK 32/45 Short'
			    151) 'QPSK 32/45 Short with Pilot'
			    152) 'QPSK 3/4 Short'
			    153) 'QPSK 3/4 Short with Pilot'
			    154) 'QPSK 4/5 Short'
			    155) 'QPSK 4/5 Short with Pilot'
			    156) 'QPSK 5/6 Short'
			    157) 'QPSK 5/6 Short with Pilot'
			    158) 'QPSK 8/9 Short'
			    159) 'QPSK 8/9 Short with Pilot'
			    160) '8PSK 7/15 Short'
			    161) '8PSK 7/15 Short with Pilot'
			    162) '8PSK 8/15 Short'
			    163) '8PSK 8/15 Short with Pilot'
			    164) '8PSK 26/45 Short'
			    165) '8PSK 26/45 Short with Pilot'
			    166) '8PSK 3/5 Short with Pilot'
			    167) '8PSK 2/3 Short with Pilot'
			    168) '8PSK 32/45 Short'
			    169) '8PSK 32/45 Short with Pilot'
			    170) '8PSK 3/4 Short'
			    171) '8PSK 3/4 Short with Pilot'
			    172) '8PSK 5/6 Short'
			    173) '8PSK 5/6 Short with Pilot'
			    174) '8PSK 8/9 Short'
			    175) '8PSK 8/9 Short with Pilot'
			    176) '16APSK 7/15 Short'
			    177) '16APSK 7/15 Short with Pilot'
			    178) '16APSK 8/15 Short'
			    179) '16APSK 8/15 Short with Pilot'
			    180) '16APSK 26/45 Short'
			    181) '16APSK 26/45 Short with Pilot'
			    182) '16APSK 3/5 Short'
			    183) '16APSK 3/5 Short with Pilot'
			    184) '16APSK 2/3 Short'
			    185) '16APSK 2/3 Short with Pilot'
			    186) '16APSK 32/45 Short'
			    187) '16APSK 32/45 Short with Pilot'
			Oid=1.3.6.1.4.1.31968.3.1.4.1.8.1.5
			"
	::= { txStatusEntry 5 }

txVcmMargin OBJECT-TYPE
	SYNTAX		Integer32
	UNITS		"0.01 dB"
	MAX-ACCESS	read-only
	STATUS		current
	DESCRIPTION "Tx Queue Remote QEF Margin
			Oid=1.3.6.1.4.1.31968.3.1.4.1.8.1.6
			"
	::= { txStatusEntry 6 }

txVcmEsn0 OBJECT-TYPE
	SYNTAX		Integer32
	UNITS		"0.01 dB"
	MAX-ACCESS	read-only
	STATUS		current
	DESCRIPTION "Tx Queue Remote Es/N0
			Oid=1.3.6.1.4.1.31968.3.1.4.1.8.1.7
			"
	::= { txStatusEntry 7 }

txVcmQueueAverage OBJECT-TYPE
	SYNTAX		Unsigned32
	UNITS		"1 bps"
	MAX-ACCESS	read-only
	STATUS		current
	DESCRIPTION "Tx Queue Average Data Rate
			Oid=1.3.6.1.4.1.31968.3.1.4.1.8.1.8
			"
	::= { txStatusEntry 8 }

txVcmQueueRate OBJECT-TYPE
	SYNTAX		Unsigned32
	UNITS		"1 bps"
	MAX-ACCESS	read-only
	STATUS		current
	DESCRIPTION "Tx Queue Data Rate
			Oid=1.3.6.1.4.1.31968.3.1.4.1.8.1.9
			"
	::= { txStatusEntry 9 }

txVcmQueuePackets OBJECT-TYPE
	SYNTAX		DisplayString(SIZE(1..24))
	UNITS		"1"
	MAX-ACCESS	read-only
	STATUS		current
	DESCRIPTION "Tx Queue Data Packets,
			    Text Number, Decimal
			Oid=1.3.6.1.4.1.31968.3.1.4.1.8.1.10
			"
	::= { txStatusEntry 10 }

txVcmQueueBytes OBJECT-TYPE
	SYNTAX		DisplayString(SIZE(1..24))
	UNITS		"1"
	MAX-ACCESS	read-only
	STATUS		current
	DESCRIPTION "Tx Queue Data Bytes,
			    Text Number, Decimal
			Oid=1.3.6.1.4.1.31968.3.1.4.1.8.1.11
			"
	::= { txStatusEntry 11 }

txVcmQueueDropped OBJECT-TYPE
	SYNTAX		DisplayString(SIZE(1..24))
	UNITS		"1"
	MAX-ACCESS	read-only
	STATUS		current
	DESCRIPTION "Tx Queue Live Packets Dropped,
			    Text Number, Decimal
			Oid=1.3.6.1.4.1.31968.3.1.4.1.8.1.12
			"
	::= { txStatusEntry 12 }

txVcmQueueFull OBJECT-TYPE
	SYNTAX		DisplayString(SIZE(1..24))
	UNITS		"1"
	MAX-ACCESS	read-only
	STATUS		current
	DESCRIPTION "Tx Queue Full Packets Dropped,
			    Text Number, Decimal
			Oid=1.3.6.1.4.1.31968.3.1.4.1.8.1.13
			"
	::= { txStatusEntry 13 }

txWaveform OBJECT-TYPE
	SYNTAX		INTEGER {
		txOff(0),
		dvbS2x(1),
		dvbS2xIqoe(2),
		ldpcGen2(3),
		segmentedLdpcGen2(4),
		ldpcHdlc(5),
		dsssLdpcGen2(6),
		mil165bDvbS2x(7),
		dvbS2xVcm(8),
		hdrTurbo(9),
		fipsValidate(10)
	}
	MAX-ACCESS	read-write
	STATUS		current
	DESCRIPTION "Tx Waveform, where:
			    0) 'Tx Off'
			    1) 'DVB-S2X'
			    2) 'DVB-S2X IQoE'
			    3) 'LDPC-Gen2'
			    4) 'Segmented LDPC-Gen2'
			    5) 'LDPC HDLC'
			    6) 'DSSS LDPC-Gen2'
			    7) 'MIL 165B DVB-S2X'
			    8) 'DVB-S2X VCM'
			    9) 'HDR Turbo'
			    10) 'FIPS Validate'
			Oid=1.3.6.1.4.1.31968.3.1.4.1.9.1
			"
	::= { txConfigItems 1 }

txTotalChannels OBJECT-TYPE
	SYNTAX		Unsigned32
	UNITS		"1"
	MAX-ACCESS	read-write
	STATUS		current
	DESCRIPTION "Tx Total Channels
			Oid=1.3.6.1.4.1.31968.3.1.4.1.9.2
			"
	::= { txConfigItems 2 }

txBucLo OBJECT-TYPE
	SYNTAX		DisplayString(SIZE(1..24))
	UNITS		"1 Hz"
	MAX-ACCESS	read-write
	STATUS		current
	DESCRIPTION "Tx BUC LO Frequency,
			    Text Number, Decimal, 0=Off
			Oid=1.3.6.1.4.1.31968.3.1.4.1.9.3
			"
	::= { txConfigItems 3 }

txBucSide OBJECT-TYPE
	SYNTAX		INTEGER {
		low(0),
		high(1)
	}
	MAX-ACCESS	read-write
	STATUS		current
	DESCRIPTION "Tx BUC LO Side, where:
			    0) 'Low'
			    1) 'High'
			Oid=1.3.6.1.4.1.31968.3.1.4.1.9.4
			"
	::= { txConfigItems 4 }

txBucRef OBJECT-TYPE
	SYNTAX		INTEGER {
		off(0),
		on(1)
	}
	MAX-ACCESS	read-write
	STATUS		current
	DESCRIPTION "Tx BUC Reference, where:
			    0) 'Off'
			    1) 'On'
			Oid=1.3.6.1.4.1.31968.3.1.4.1.9.5
			"
	::= { txConfigItems 5 }

txBucCenterFrequency OBJECT-TYPE
	SYNTAX		DisplayString(SIZE(1..24))
	UNITS		"1 Hz"
	MAX-ACCESS	read-write
	STATUS		current
	DESCRIPTION "Tx BUC Center Frequency,
			    Text Number, Decimal
			Oid=1.3.6.1.4.1.31968.3.1.4.1.9.6
			"
	::= { txConfigItems 6 }

txCenterFrequency OBJECT-TYPE
	SYNTAX		Unsigned32
	UNITS		"1 Hz"
	MAX-ACCESS	read-write
	STATUS		current
	DESCRIPTION "Tx Center Frequency
			Oid=1.3.6.1.4.1.31968.3.1.4.1.9.7
			"
	::= { txConfigItems 7 }

txTotalMinSymbolRate OBJECT-TYPE
	SYNTAX		Unsigned32
	UNITS		"1 sps"
	MAX-ACCESS	read-write
	STATUS		current
	DESCRIPTION "Tx Total Min Symbol Rate
			Oid=1.3.6.1.4.1.31968.3.1.4.1.9.8
			"
	::= { txConfigItems 8 }

txTotalMaxSymbolRate OBJECT-TYPE
	SYNTAX		Unsigned32
	UNITS		"1 sps"
	MAX-ACCESS	read-write
	STATUS		current
	DESCRIPTION "Tx Total Max Symbol Rate
			Oid=1.3.6.1.4.1.31968.3.1.4.1.9.9
			"
	::= { txConfigItems 9 }

txPsdLevel OBJECT-TYPE
	SYNTAX		Integer32
	UNITS		"0.01 dBm/Hz"
	MAX-ACCESS	read-write
	STATUS		current
	DESCRIPTION "Tx Nominal PSD Level
			Oid=1.3.6.1.4.1.31968.3.1.4.1.9.10
			"
	::= { txConfigItems 10 }

txLevel OBJECT-TYPE
	SYNTAX		Integer32
	UNITS		"0.01 dBm"
	MAX-ACCESS	read-write
	STATUS		current
	DESCRIPTION "Tx Level
			Oid=1.3.6.1.4.1.31968.3.1.4.1.9.11
			"
	::= { txConfigItems 11 }

txMute OBJECT-TYPE
	SYNTAX		INTEGER {
		automatic(0),
		confirm(1),
		manual(2),
		manualAndPowerLoss(3)
	}
	MAX-ACCESS	read-write
	STATUS		current
	DESCRIPTION "Tx Mute, where:
			    0) 'Automatic'
			    1) 'Confirm'
			    2) 'Manual'
			    3) 'Manual & Power Loss'
			Oid=1.3.6.1.4.1.31968.3.1.4.1.9.12
			"
	::= { txConfigItems 12 }

txRollOff OBJECT-TYPE
	SYNTAX		INTEGER {
		n35Percent(0),
		n30Percent(1),
		n25Percent(2),
		n20Percent(3),
		n15Percent(4),
		n10Percent(5),
		n5Percent(6),
		n2Percent(7),
		n40Percent(8),
		n45Percent(9)
	}
	MAX-ACCESS	read-write
	STATUS		current
	DESCRIPTION "Tx Roll-Off, where:
			    0) '35%'
			    1) '30%'
			    2) '25%'
			    3) '20%'
			    4) '15%'
			    5) '10%'
			    6) '5%'
			    7) '2%'
			    8) '40%'
			    9) '45%'
			Oid=1.3.6.1.4.1.31968.3.1.4.1.9.13
			"
	::= { txConfigItems 13 }

txSpectrum OBJECT-TYPE
	SYNTAX		INTEGER {
		normal(0),
		inverted(1)
	}
	MAX-ACCESS	read-write
	STATUS		current
	DESCRIPTION "Tx Spectrum, where:
			    0) 'Normal'
			    1) 'Inverted'
			Oid=1.3.6.1.4.1.31968.3.1.4.1.9.14
			"
	::= { txConfigItems 14 }

txTilt OBJECT-TYPE
	SYNTAX		Integer32
	UNITS		"0.01 dB"
	MAX-ACCESS	read-write
	STATUS		current
	DESCRIPTION "Tx Tilt
			Oid=1.3.6.1.4.1.31968.3.1.4.1.9.15
			"
	::= { txConfigItems 15 }

txAupc OBJECT-TYPE
	SYNTAX		INTEGER {
		off(0),
		on(1)
	}
	MAX-ACCESS	read-write
	STATUS		current
	DESCRIPTION "Tx AUPC, where:
			    0) 'Off'
			    1) 'On'
			Oid=1.3.6.1.4.1.31968.3.1.4.1.9.16
			"
	::= { txConfigItems 16 }

txAupcEsn0 OBJECT-TYPE
	SYNTAX		Integer32
	UNITS		"0.01 dB"
	MAX-ACCESS	read-write
	STATUS		current
	DESCRIPTION "Tx AUPC Es/N0
			Oid=1.3.6.1.4.1.31968.3.1.4.1.9.17
			"
	::= { txConfigItems 17 }

txAupcMin OBJECT-TYPE
	SYNTAX		Integer32
	UNITS		"0.01 dBm"
	MAX-ACCESS	read-write
	STATUS		current
	DESCRIPTION "Tx AUPC Min Level
			Oid=1.3.6.1.4.1.31968.3.1.4.1.9.18
			"
	::= { txConfigItems 18 }

txAupcMax OBJECT-TYPE
	SYNTAX		Integer32
	UNITS		"0.01 dBm"
	MAX-ACCESS	read-write
	STATUS		current
	DESCRIPTION "Tx AUPC Max Level
			Oid=1.3.6.1.4.1.31968.3.1.4.1.9.19
			"
	::= { txConfigItems 19 }

txAupcLimitAlarm OBJECT-TYPE
	SYNTAX		INTEGER {
		off(0),
		report(1),
		alarm(3),
		alarmAndRelayOutput(5)
	}
	MAX-ACCESS	read-write
	STATUS		current
	DESCRIPTION "Tx AUPC Maximum Limit Alarm, where:
			    0) 'Off'
			    1) 'Report'
			    3) 'Alarm'
			    5) 'Alarm & Relay Output'
			Oid=1.3.6.1.4.1.31968.3.1.4.1.9.20
			"
	::= { txConfigItems 20 }

txTrafficStatsReset OBJECT-TYPE
	SYNTAX		INTEGER {
		statsRunning(0),
		resetSelfClearing(1)
	}
	MAX-ACCESS	read-write
	STATUS		current
	DESCRIPTION "Tx Traffic Statistics Reset, where:
			    0) 'Stats Running...'
			    1) 'Reset - Self Clearing'
			Oid=1.3.6.1.4.1.31968.3.1.4.1.9.21
			"
	::= { txConfigItems 21 }

txDvbService OBJECT-TYPE
	SYNTAX		INTEGER {
		dvbS2(0),
		dvbS2AcmPreferred(1),
		dvbS2x(2),
		dvbS2xAcmPreferred(3),
		dvbS2xAcmPreferredL(4)
	}
	MAX-ACCESS	read-write
	STATUS		current
	DESCRIPTION "Tx Service, where:
			    0) 'DVB-S2'
			    1) 'DVB-S2 ACM Preferred'
			    2) 'DVB-S2X'
			    3) 'DVB-S2X ACM Preferred'
			    4) 'DVB-S2X ACM Preferred-L'
			Oid=1.3.6.1.4.1.31968.3.1.4.1.9.24
			"
	::= { txConfigItems 24 }

txDvbFrame OBJECT-TYPE
	SYNTAX		INTEGER {
		normal(0),
		short(1)
	}
	MAX-ACCESS	read-write
	STATUS		current
	DESCRIPTION "Tx Frame Size, where:
			    0) 'Normal'
			    1) 'Short'
			Oid=1.3.6.1.4.1.31968.3.1.4.1.9.25
			"
	::= { txConfigItems 25 }

txDvbPilot OBJECT-TYPE
	SYNTAX		INTEGER {
		auto(0),
		on(1)
	}
	MAX-ACCESS	read-write
	STATUS		current
	DESCRIPTION "Tx Pilot, where:
			    0) 'Auto'
			    1) 'On'
			Oid=1.3.6.1.4.1.31968.3.1.4.1.9.26
			"
	::= { txConfigItems 26 }

txDvbFixedModcod OBJECT-TYPE
	SYNTAX		INTEGER {
		qpsk1x4Normal(0),
		qpsk1x4NormalWithPilot(1),
		qpsk13x45Normal(2),
		qpsk13x45NormalWithPilot(3),
		qpsk1x3Normal(4),
		qpsk1x3NormalWithPilot(5),
		qpsk2x5Normal(6),
		qpsk2x5NormalWithPilot(7),
		qpsk9x20Normal(8),
		qpsk9x20NormalWithPilot(9),
		qpsk1x2Normal(10),
		qpsk1x2NormalWithPilot(11),
		qpsk11x20Normal(12),
		qpsk11x20NormalWithPilot(13),
		qpsk3x5Normal(14),
		qpsk3x5NormalWithPilot(15),
		qpsk2x3Normal(16),
		qpsk2x3NormalWithPilot(17),
		qpsk3x4Normal(18),
		qpsk3x4NormalWithPilot(19),
		qpsk4x5Normal(20),
		qpsk4x5NormalWithPilot(21),
		qpsk5x6Normal(22),
		qpsk5x6NormalWithPilot(23),
		qpsk8x9Normal(24),
		qpsk8x9NormalWithPilot(25),
		qpsk9x10Normal(26),
		qpsk9x10NormalWithPilot(27),
		n8apsk5x9LNormal(28),
		n8apsk5x9LNormalWithPilot(29),
		n8apsk26x45LNormal(30),
		n8apsk26x45LNormalWithPilot(31),
		n8psk3x5NormalWithPilot(32),
		n8psk23x36Normal(33),
		n8psk23x36NormalWithPilot(34),
		n8psk2x3NormalWithPilot(35),
		n8psk25x36Normal(36),
		n8psk25x36NormalWithPilot(37),
		n8psk13x18Normal(38),
		n8psk13x18NormalWithPilot(39),
		n8psk3x4Normal(40),
		n8psk3x4NormalWithPilot(41),
		n8psk5x6Normal(42),
		n8psk5x6NormalWithPilot(43),
		n8psk8x9Normal(44),
		n8psk8x9NormalWithPilot(45),
		n8psk9x10Normal(46),
		n8psk9x10NormalWithPilot(47),
		n16apsk1x2LNormal(48),
		n16apsk1x2LNormalWithPilot(49),
		n16apsk8x15LNormal(50),
		n16apsk8x15LNormalWithPilot(51),
		n16apsk5x9LNormal(52),
		n16apsk5x9LNormalWithPilot(53),
		n16apsk26x45Normal(54),
		n16apsk26x45NormalWithPilot(55),
		n16apsk3x5Normal(56),
		n16apsk3x5NormalWithPilot(57),
		n16apsk3x5LNormal(58),
		n16apsk3x5LNormalWithPilot(59),
		n16apsk28x45Normal(60),
		n16apsk28x45NormalWithPilot(61),
		n16apsk23x36Normal(62),
		n16apsk23x36NormalWithPilot(63),
		n16apsk2x3LNormal(64),
		n16apsk2x3LNormalWithPilot(65),
		n16apsk2x3Normal(66),
		n16apsk2x3NormalWithPilot(67),
		n16apsk25x36Normal(68),
		n16apsk25x36NormalWithPilot(69),
		n16apsk13x18Normal(70),
		n16apsk13x18NormalWithPilot(71),
		n16apsk3x4NormalWithPilot(72),
		n16apsk7x9Normal(73),
		n16apsk7x9NormalWithPilot(74),
		n16apsk4x5Normal(75),
		n16apsk4x5NormalWithPilot(76),
		n16apsk5x6Normal(77),
		n16apsk5x6NormalWithPilot(78),
		n16apsk77x90Normal(79),
		n16apsk77x90NormalWithPilot(80),
		n16apsk8x9Normal(81),
		n16apsk8x9NormalWithPilot(82),
		n16apsk9x10Normal(83),
		n16apsk9x10NormalWithPilot(84),
		n32apsk2x3LNormal(85),
		n32apsk2x3LNormalWithPilot(86),
		n32apsk32x45Normal(87),
		n32apsk32x45NormalWithPilot(88),
		n32apsk11x15Normal(89),
		n32apsk11x15NormalWithPilot(90),
		n32apsk3x4Normal(91),
		n32apsk3x4NormalWithPilot(92),
		n32apsk7x9Normal(93),
		n32apsk7x9NormalWithPilot(94),
		n32apsk4x5NormalWithPilot(95),
		n32apsk5x6Normal(96),
		n32apsk5x6NormalWithPilot(97),
		n32apsk8x9Normal(98),
		n32apsk8x9NormalWithPilot(99),
		n32apsk9x10Normal(100),
		n32apsk9x10NormalWithPilot(101),
		n64apsk32x45LNormal(102),
		n64apsk32x45LNormalWithPilot(103),
		n64apsk11x15Normal(104),
		n64apsk11x15NormalWithPilot(105),
		n64apsk7x9Normal(106),
		n64apsk7x9NormalWithPilot(107),
		n64apsk4x5Normal(108),
		n64apsk4x5NormalWithPilot(109),
		n64apsk5x6Normal(110),
		n64apsk5x6NormalWithPilot(111),
		n128apsk3x4Normal(112),
		n128apsk3x4NormalWithPilot(113),
		n128apsk7x9Normal(114),
		n128apsk7x9NormalWithPilot(115),
		n256apsk29x45LNormal(116),
		n256apsk29x45LNormalWithPilot(117),
		n256apsk2x3LNormal(118),
		n256apsk2x3LNormalWithPilot(119),
		n256apsk31x45LNormal(120),
		n256apsk31x45LNormalWithPilot(121),
		n256apsk32x45Normal(122),
		n256apsk32x45NormalWithPilot(123),
		n256apsk11x15LNormal(124),
		n256apsk11x15LNormalWithPilot(125),
		n256apsk3x4Normal(126),
		n256apsk3x4NormalWithPilot(127),
		qpsk1x4Short(128),
		qpsk1x4ShortWithPilot(129),
		qpsk11x45Short(130),
		qpsk11x45ShortWithPilot(131),
		qpsk4x15Short(132),
		qpsk4x15ShortWithPilot(133),
		qpsk14x45Short(134),
		qpsk14x45ShortWithPilot(135),
		qpsk1x3Short(136),
		qpsk1x3ShortWithPilot(137),
		qpsk2x5Short(138),
		qpsk2x5ShortWithPilot(139),
		qpsk1x2Short(140),
		qpsk1x2ShortWithPilot(141),
		qpsk7x15Short(142),
		qpsk7x15ShortWithPilot(143),
		qpsk8x15Short(144),
		qpsk8x15ShortWithPilot(145),
		qpsk3x5Short(146),
		qpsk3x5ShortWithPilot(147),
		qpsk2x3Short(148),
		qpsk2x3ShortWithPilot(149),
		qpsk32x45Short(150),
		qpsk32x45ShortWithPilot(151),
		qpsk3x4Short(152),
		qpsk3x4ShortWithPilot(153),
		qpsk4x5Short(154),
		qpsk4x5ShortWithPilot(155),
		qpsk5x6Short(156),
		qpsk5x6ShortWithPilot(157),
		qpsk8x9Short(158),
		qpsk8x9ShortWithPilot(159),
		n8psk7x15Short(160),
		n8psk7x15ShortWithPilot(161),
		n8psk8x15Short(162),
		n8psk8x15ShortWithPilot(163),
		n8psk26x45Short(164),
		n8psk26x45ShortWithPilot(165),
		n8psk3x5ShortWithPilot(166),
		n8psk2x3ShortWithPilot(167),
		n8psk32x45Short(168),
		n8psk32x45ShortWithPilot(169),
		n8psk3x4Short(170),
		n8psk3x4ShortWithPilot(171),
		n8psk5x6Short(172),
		n8psk5x6ShortWithPilot(173),
		n8psk8x9Short(174),
		n8psk8x9ShortWithPilot(175),
		n16apsk7x15Short(176),
		n16apsk7x15ShortWithPilot(177),
		n16apsk8x15Short(178),
		n16apsk8x15ShortWithPilot(179),
		n16apsk26x45Short(180),
		n16apsk26x45ShortWithPilot(181),
		n16apsk3x5Short(182),
		n16apsk3x5ShortWithPilot(183),
		n16apsk2x3Short(184),
		n16apsk2x3ShortWithPilot(185),
		n16apsk32x45Short(186),
		n16apsk32x45ShortWithPilot(187),
		n16apsk3x4ShortWithPilot(188),
		n16apsk4x5Short(189),
		n16apsk4x5ShortWithPilot(190),
		n16apsk5x6Short(191),
		n16apsk5x6ShortWithPilot(192),
		n16apsk8x9Short(193),
		n16apsk8x9ShortWithPilot(194),
		n32apsk2x3Short(195),
		n32apsk2x3ShortWithPilot(196),
		n32apsk32x45Short(197),
		n32apsk32x45ShortWithPilot(198),
		n32apsk3x4Short(199),
		n32apsk3x4ShortWithPilot(200),
		n32apsk4x5ShortWithPilot(201),
		n32apsk5x6Short(202),
		n32apsk5x6ShortWithPilot(203),
		n32apsk8x9Short(204),
		n32apsk8x9ShortWithPilot(205)
	}
	MAX-ACCESS	read-write
	STATUS		current
	DESCRIPTION "Tx ModCod, where:
			    0) 'QPSK 1/4 Normal'
			    1) 'QPSK 1/4 Normal with Pilot'
			    2) 'QPSK 13/45 Normal'
			    3) 'QPSK 13/45 Normal with Pilot'
			    4) 'QPSK 1/3 Normal'
			    5) 'QPSK 1/3 Normal with Pilot'
			    6) 'QPSK 2/5 Normal'
			    7) 'QPSK 2/5 Normal with Pilot'
			    8) 'QPSK 9/20 Normal'
			    9) 'QPSK 9/20 Normal with Pilot'
			    10) 'QPSK 1/2 Normal'
			    11) 'QPSK 1/2 Normal with Pilot'
			    12) 'QPSK 11/20 Normal'
			    13) 'QPSK 11/20 Normal with Pilot'
			    14) 'QPSK 3/5 Normal'
			    15) 'QPSK 3/5 Normal with Pilot'
			    16) 'QPSK 2/3 Normal'
			    17) 'QPSK 2/3 Normal with Pilot'
			    18) 'QPSK 3/4 Normal'
			    19) 'QPSK 3/4 Normal with Pilot'
			    20) 'QPSK 4/5 Normal'
			    21) 'QPSK 4/5 Normal with Pilot'
			    22) 'QPSK 5/6 Normal'
			    23) 'QPSK 5/6 Normal with Pilot'
			    24) 'QPSK 8/9 Normal'
			    25) 'QPSK 8/9 Normal with Pilot'
			    26) 'QPSK 9/10 Normal'
			    27) 'QPSK 9/10 Normal with Pilot'
			    28) '8APSK 5/9-L Normal'
			    29) '8APSK 5/9-L Normal with Pilot'
			    30) '8APSK 26/45-L Normal'
			    31) '8APSK 26/45-L Normal with Pilot'
			    32) '8PSK 3/5 Normal with Pilot'
			    33) '8PSK 23/36 Normal'
			    34) '8PSK 23/36 Normal with Pilot'
			    35) '8PSK 2/3 Normal with Pilot'
			    36) '8PSK 25/36 Normal'
			    37) '8PSK 25/36 Normal with Pilot'
			    38) '8PSK 13/18 Normal'
			    39) '8PSK 13/18 Normal with Pilot'
			    40) '8PSK 3/4 Normal'
			    41) '8PSK 3/4 Normal with Pilot'
			    42) '8PSK 5/6 Normal'
			    43) '8PSK 5/6 Normal with Pilot'
			    44) '8PSK 8/9 Normal'
			    45) '8PSK 8/9 Normal with Pilot'
			    46) '8PSK 9/10 Normal'
			    47) '8PSK 9/10 Normal with Pilot'
			    48) '16APSK 1/2-L Normal'
			    49) '16APSK 1/2-L Normal with Pilot'
			    50) '16APSK 8/15-L Normal'
			    51) '16APSK 8/15-L Normal with Pilot'
			    52) '16APSK 5/9-L Normal'
			    53) '16APSK 5/9-L Normal with Pilot'
			    54) '16APSK 26/45 Normal'
			    55) '16APSK 26/45 Normal with Pilot'
			    56) '16APSK 3/5 Normal'
			    57) '16APSK 3/5 Normal with Pilot'
			    58) '16APSK 3/5-L Normal'
			    59) '16APSK 3/5-L Normal with Pilot'
			    60) '16APSK 28/45 Normal'
			    61) '16APSK 28/45 Normal with Pilot'
			    62) '16APSK 23/36 Normal'
			    63) '16APSK 23/36 Normal with Pilot'
			    64) '16APSK 2/3-L Normal'
			    65) '16APSK 2/3-L Normal with Pilot'
			    66) '16APSK 2/3 Normal'
			    67) '16APSK 2/3 Normal with Pilot'
			    68) '16APSK 25/36 Normal'
			    69) '16APSK 25/36 Normal with Pilot'
			    70) '16APSK 13/18 Normal'
			    71) '16APSK 13/18 Normal with Pilot'
			    72) '16APSK 3/4 Normal with Pilot'
			    73) '16APSK 7/9 Normal'
			    74) '16APSK 7/9 Normal with Pilot'
			    75) '16APSK 4/5 Normal'
			    76) '16APSK 4/5 Normal with Pilot'
			    77) '16APSK 5/6 Normal'
			    78) '16APSK 5/6 Normal with Pilot'
			    79) '16APSK 77/90 Normal'
			    80) '16APSK 77/90 Normal with Pilot'
			    81) '16APSK 8/9 Normal'
			    82) '16APSK 8/9 Normal with Pilot'
			    83) '16APSK 9/10 Normal'
			    84) '16APSK 9/10 Normal with Pilot'
			    85) '32APSK 2/3-L Normal'
			    86) '32APSK 2/3-L Normal with Pilot'
			    87) '32APSK 32/45 Normal'
			    88) '32APSK 32/45 Normal with Pilot'
			    89) '32APSK 11/15 Normal'
			    90) '32APSK 11/15 Normal with Pilot'
			    91) '32APSK 3/4 Normal'
			    92) '32APSK 3/4 Normal with Pilot'
			    93) '32APSK 7/9 Normal'
			    94) '32APSK 7/9 Normal with Pilot'
			    95) '32APSK 4/5 Normal with Pilot'
			    96) '32APSK 5/6 Normal'
			    97) '32APSK 5/6 Normal with Pilot'
			    98) '32APSK 8/9 Normal'
			    99) '32APSK 8/9 Normal with Pilot'
			    100) '32APSK 9/10 Normal'
			    101) '32APSK 9/10 Normal with Pilot'
			    102) '64APSK 32/45-L Normal'
			    103) '64APSK 32/45-L Normal with Pilot'
			    104) '64APSK 11/15 Normal'
			    105) '64APSK 11/15 Normal with Pilot'
			    106) '64APSK 7/9 Normal'
			    107) '64APSK 7/9 Normal with Pilot'
			    108) '64APSK 4/5 Normal'
			    109) '64APSK 4/5 Normal with Pilot'
			    110) '64APSK 5/6 Normal'
			    111) '64APSK 5/6 Normal with Pilot'
			    112) '128APSK 3/4 Normal'
			    113) '128APSK 3/4 Normal with Pilot'
			    114) '128APSK 7/9 Normal'
			    115) '128APSK 7/9 Normal with Pilot'
			    116) '256APSK 29/45-L Normal'
			    117) '256APSK 29/45-L Normal with Pilot'
			    118) '256APSK 2/3-L Normal'
			    119) '256APSK 2/3-L Normal with Pilot'
			    120) '256APSK 31/45-L Normal'
			    121) '256APSK 31/45-L Normal with Pilot'
			    122) '256APSK 32/45 Normal'
			    123) '256APSK 32/45 Normal with Pilot'
			    124) '256APSK 11/15-L Normal'
			    125) '256APSK 11/15-L Normal with Pilot'
			    126) '256APSK 3/4 Normal'
			    127) '256APSK 3/4 Normal with Pilot'
			    128) 'QPSK 1/4 Short'
			    129) 'QPSK 1/4 Short with Pilot'
			    130) 'QPSK 11/45 Short'
			    131) 'QPSK 11/45 Short with Pilot'
			    132) 'QPSK 4/15 Short'
			    133) 'QPSK 4/15 Short with Pilot'
			    134) 'QPSK 14/45 Short'
			    135) 'QPSK 14/45 Short with Pilot'
			    136) 'QPSK 1/3 Short'
			    137) 'QPSK 1/3 Short with Pilot'
			    138) 'QPSK 2/5 Short'
			    139) 'QPSK 2/5 Short with Pilot'
			    140) 'QPSK 1/2 Short'
			    141) 'QPSK 1/2 Short with Pilot'
			    142) 'QPSK 7/15 Short'
			    143) 'QPSK 7/15 Short with Pilot'
			    144) 'QPSK 8/15 Short'
			    145) 'QPSK 8/15 Short with Pilot'
			    146) 'QPSK 3/5 Short'
			    147) 'QPSK 3/5 Short with Pilot'
			    148) 'QPSK 2/3 Short'
			    149) 'QPSK 2/3 Short with Pilot'
			    150) 'QPSK 32/45 Short'
			    151) 'QPSK 32/45 Short with Pilot'
			    152) 'QPSK 3/4 Short'
			    153) 'QPSK 3/4 Short with Pilot'
			    154) 'QPSK 4/5 Short'
			    155) 'QPSK 4/5 Short with Pilot'
			    156) 'QPSK 5/6 Short'
			    157) 'QPSK 5/6 Short with Pilot'
			    158) 'QPSK 8/9 Short'
			    159) 'QPSK 8/9 Short with Pilot'
			    160) '8PSK 7/15 Short'
			    161) '8PSK 7/15 Short with Pilot'
			    162) '8PSK 8/15 Short'
			    163) '8PSK 8/15 Short with Pilot'
			    164) '8PSK 26/45 Short'
			    165) '8PSK 26/45 Short with Pilot'
			    166) '8PSK 3/5 Short with Pilot'
			    167) '8PSK 2/3 Short with Pilot'
			    168) '8PSK 32/45 Short'
			    169) '8PSK 32/45 Short with Pilot'
			    170) '8PSK 3/4 Short'
			    171) '8PSK 3/4 Short with Pilot'
			    172) '8PSK 5/6 Short'
			    173) '8PSK 5/6 Short with Pilot'
			    174) '8PSK 8/9 Short'
			    175) '8PSK 8/9 Short with Pilot'
			    176) '16APSK 7/15 Short'
			    177) '16APSK 7/15 Short with Pilot'
			    178) '16APSK 8/15 Short'
			    179) '16APSK 8/15 Short with Pilot'
			    180) '16APSK 26/45 Short'
			    181) '16APSK 26/45 Short with Pilot'
			    182) '16APSK 3/5 Short'
			    183) '16APSK 3/5 Short with Pilot'
			    184) '16APSK 2/3 Short'
			    185) '16APSK 2/3 Short with Pilot'
			    186) '16APSK 32/45 Short'
			    187) '16APSK 32/45 Short with Pilot'
			    188) '16APSK 3/4 Short with Pilot'
			    189) '16APSK 4/5 Short'
			    190) '16APSK 4/5 Short with Pilot'
			    191) '16APSK 5/6 Short'
			    192) '16APSK 5/6 Short with Pilot'
			    193) '16APSK 8/9 Short'
			    194) '16APSK 8/9 Short with Pilot'
			    195) '32APSK 2/3 Short'
			    196) '32APSK 2/3 Short with Pilot'
			    197) '32APSK 32/45 Short'
			    198) '32APSK 32/45 Short with Pilot'
			    199) '32APSK 3/4 Short'
			    200) '32APSK 3/4 Short with Pilot'
			    201) '32APSK 4/5 Short with Pilot'
			    202) '32APSK 5/6 Short'
			    203) '32APSK 5/6 Short with Pilot'
			    204) '32APSK 8/9 Short'
			    205) '32APSK 8/9 Short with Pilot'
			Oid=1.3.6.1.4.1.31968.3.1.4.1.9.27
			"
	::= { txConfigItems 27 }

txDvbScrambler OBJECT-TYPE
	SYNTAX		Unsigned32
	UNITS		"1"
	MAX-ACCESS	read-write
	STATUS		current
	DESCRIPTION "Tx PLS Scrambler Sequence
			Oid=1.3.6.1.4.1.31968.3.1.4.1.9.28
			"
	::= { txConfigItems 28 }

txLdpcService OBJECT-TYPE
	SYNTAX		INTEGER {
		ldpcGen2(0),
		ldpcGen2Acm(1)
	}
	MAX-ACCESS	read-write
	STATUS		current
	DESCRIPTION "Tx Service, where:
			    0) 'LDPC-Gen2'
			    1) 'LDPC-Gen2 ACM'
			Oid=1.3.6.1.4.1.31968.3.1.4.1.9.29
			"
	::= { txConfigItems 29 }

txLdpcBlock OBJECT-TYPE
	SYNTAX		INTEGER {
		n2k(0),
		n4k(1),
		n8k(2),
		n16k(3)
	}
	MAX-ACCESS	read-write
	STATUS		current
	DESCRIPTION "Tx Block Size, where:
			    0) '2k'
			    1) '4k'
			    2) '8k'
			    3) '16k'
			Oid=1.3.6.1.4.1.31968.3.1.4.1.9.30
			"
	::= { txConfigItems 30 }

txLdpcFixedModcod OBJECT-TYPE
	SYNTAX		INTEGER {
		bpsk1x2(0),
		bpsk8x15(1),
		bpsk4x7(2),
		bpsk8x13(3),
		bpsk2x3(4),
		bpsk16x23(5),
		bpsk8x11(6),
		qpsk1x2(7),
		qpsk8x15(8),
		qpsk4x7(9),
		qpsk8x13(10),
		qpsk2x3(11),
		qpsk16x23(12),
		qpsk8x11(13),
		qpsk16x21(14),
		qpsk4x5(15),
		qpsk16x19(16),
		qpsk8x9(17),
		n8psk8x13(18),
		n8psk2x3(19),
		n8psk16x23(20),
		n8apsk8x13(21),
		n8apsk2x3(22),
		n8apsk16x23(23),
		n16apsk4x7(24),
		n16apsk8x13(25),
		n16apsk2x3(26),
		n16apsk16x23(27),
		n16apsk8x11(28),
		n16apsk16x21(29),
		n16apsk4x5(30),
		n16apsk16x19(31),
		n16apsk8x9(32),
		n16apsk16x17(33),
		n16qam1x2(34),
		n16qam8x15(35),
		n16qam4x7(36),
		n16qam8x13(37),
		n16qam2x3(38),
		n16qam16x23(39),
		n16qam8x11(40),
		n16qam16x21(41),
		n16qam4x5(42),
		n16qam16x19(43),
		n16qam8x9(44),
		n16qam16x17(45),
		n32qam2x3(46),
		n32qam16x23(47),
		n32qam8x11(48),
		n32qam16x21(49),
		n32qam4x5(50),
		n32qam16x19(51),
		n32qam8x9(52),
		n32qam16x17(53),
		n64qam2x3(54),
		n64qam16x23(55),
		n64qam8x11(56),
		n64qam16x21(57),
		n64qam4x5(58),
		n64qam16x19(59),
		n64qam8x9(60),
		n64qam16x17(61)
	}
	MAX-ACCESS	read-write
	STATUS		current
	DESCRIPTION "Tx ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'QPSK 1/2'
			    8) 'QPSK 8/15'
			    9) 'QPSK 4/7'
			    10) 'QPSK 8/13'
			    11) 'QPSK 2/3'
			    12) 'QPSK 16/23'
			    13) 'QPSK 8/11'
			    14) 'QPSK 16/21'
			    15) 'QPSK 4/5'
			    16) 'QPSK 16/19'
			    17) 'QPSK 8/9'
			    18) '8PSK 8/13'
			    19) '8PSK 2/3'
			    20) '8PSK 16/23'
			    21) '8APSK 8/13'
			    22) '8APSK 2/3'
			    23) '8APSK 16/23'
			    24) '16APSK 4/7'
			    25) '16APSK 8/13'
			    26) '16APSK 2/3'
			    27) '16APSK 16/23'
			    28) '16APSK 8/11'
			    29) '16APSK 16/21'
			    30) '16APSK 4/5'
			    31) '16APSK 16/19'
			    32) '16APSK 8/9'
			    33) '16APSK 16/17'
			    34) '16QAM 1/2'
			    35) '16QAM 8/15'
			    36) '16QAM 4/7'
			    37) '16QAM 8/13'
			    38) '16QAM 2/3'
			    39) '16QAM 16/23'
			    40) '16QAM 8/11'
			    41) '16QAM 16/21'
			    42) '16QAM 4/5'
			    43) '16QAM 16/19'
			    44) '16QAM 8/9'
			    45) '16QAM 16/17'
			    46) '32QAM 2/3'
			    47) '32QAM 16/23'
			    48) '32QAM 8/11'
			    49) '32QAM 16/21'
			    50) '32QAM 4/5'
			    51) '32QAM 16/19'
			    52) '32QAM 8/9'
			    53) '32QAM 16/17'
			    54) '64QAM 2/3'
			    55) '64QAM 16/23'
			    56) '64QAM 8/11'
			    57) '64QAM 16/21'
			    58) '64QAM 4/5'
			    59) '64QAM 16/19'
			    60) '64QAM 8/9'
			    61) '64QAM 16/17'
			Oid=1.3.6.1.4.1.31968.3.1.4.1.9.31
			"
	::= { txConfigItems 31 }

txLdpcScrambler OBJECT-TYPE
	SYNTAX		INTEGER {
		off(0),
		asynchronous(1),
		fecFrameSynchronous(2)
	}
	MAX-ACCESS	read-write
	STATUS		current
	DESCRIPTION "Tx Scrambler, where:
			    0) 'Off'
			    1) 'Asynchronous'
			    2) 'FEC Frame Synchronous'
			Oid=1.3.6.1.4.1.31968.3.1.4.1.9.32
			"
	::= { txConfigItems 32 }

txAcmMinEsn0 OBJECT-TYPE
	SYNTAX		Integer32
	UNITS		"0.01 dB"
	MAX-ACCESS	read-write
	STATUS		current
	DESCRIPTION "Tx ACM Min Es/N0
			Oid=1.3.6.1.4.1.31968.3.1.4.1.9.33
			"
	::= { txConfigItems 33 }

txAcmMaxEsn0 OBJECT-TYPE
	SYNTAX		Integer32
	UNITS		"0.01 dB"
	MAX-ACCESS	read-write
	STATUS		current
	DESCRIPTION "Tx ACM Max Es/N0
			Oid=1.3.6.1.4.1.31968.3.1.4.1.9.34
			"
	::= { txConfigItems 34 }

txAcmLowEsn0Alarm OBJECT-TYPE
	SYNTAX		INTEGER {
		off(0),
		report(1),
		alarm(3),
		alarmAndRelayOutput(5)
	}
	MAX-ACCESS	read-write
	STATUS		current
	DESCRIPTION "Tx ACM Low Es/N0 Alarm - ACR Low SNR Alarm, where:
			    0) 'Off'
			    1) 'Report'
			    3) 'Alarm'
			    5) 'Alarm & Relay Output'
			Oid=1.3.6.1.4.1.31968.3.1.4.1.9.35
			"
	::= { txConfigItems 35 }

txAcmLowEsn0Limit OBJECT-TYPE
	SYNTAX		Integer32
	UNITS		"0.01 dB"
	MAX-ACCESS	read-write
	STATUS		current
	DESCRIPTION "Tx ACM Low Es/N0 Limit
			Oid=1.3.6.1.4.1.31968.3.1.4.1.9.36
			"
	::= { txConfigItems 36 }

txMccChannelAlarm OBJECT-TYPE
	SYNTAX		INTEGER {
		off(0),
		report(1),
		alarm(3),
		alarmAndRelayOutput(5)
	}
	MAX-ACCESS	read-write
	STATUS		current
	DESCRIPTION "Tx MCC Remote Channel Alarm, where:
			    0) 'Off'
			    1) 'Report'
			    3) 'Alarm'
			    5) 'Alarm & Relay Output'
			Oid=1.3.6.1.4.1.31968.3.1.4.1.9.37
			"
	::= { txConfigItems 37 }

txAcm2aryHysteresis OBJECT-TYPE
	SYNTAX		Unsigned32
	UNITS		"0.01 dB"
	MAX-ACCESS	read-write
	STATUS		current
	DESCRIPTION "Tx ACM 2-ary Hysteresis
			Oid=1.3.6.1.4.1.31968.3.1.4.1.9.38
			"
	::= { txConfigItems 38 }

txAcm4aryHysteresis OBJECT-TYPE
	SYNTAX		Unsigned32
	UNITS		"0.01 dB"
	MAX-ACCESS	read-write
	STATUS		current
	DESCRIPTION "Tx ACM 4-ary Hysteresis
			Oid=1.3.6.1.4.1.31968.3.1.4.1.9.39
			"
	::= { txConfigItems 39 }

txAcm8aryHysteresis OBJECT-TYPE
	SYNTAX		Unsigned32
	UNITS		"0.01 dB"
	MAX-ACCESS	read-write
	STATUS		current
	DESCRIPTION "Tx ACM 8-ary Hysteresis
			Oid=1.3.6.1.4.1.31968.3.1.4.1.9.40
			"
	::= { txConfigItems 40 }

txAcm16aryHysteresis OBJECT-TYPE
	SYNTAX		Unsigned32
	UNITS		"0.01 dB"
	MAX-ACCESS	read-write
	STATUS		current
	DESCRIPTION "Tx ACM 16-ary Hysteresis
			Oid=1.3.6.1.4.1.31968.3.1.4.1.9.41
			"
	::= { txConfigItems 41 }

txAcm32aryHysteresis OBJECT-TYPE
	SYNTAX		Unsigned32
	UNITS		"0.01 dB"
	MAX-ACCESS	read-write
	STATUS		current
	DESCRIPTION "Tx ACM 32-ary Hysteresis
			Oid=1.3.6.1.4.1.31968.3.1.4.1.9.42
			"
	::= { txConfigItems 42 }

txAcm64aryHysteresis OBJECT-TYPE
	SYNTAX		Unsigned32
	UNITS		"0.01 dB"
	MAX-ACCESS	read-write
	STATUS		current
	DESCRIPTION "Tx ACM 64-ary Hysteresis
			Oid=1.3.6.1.4.1.31968.3.1.4.1.9.43
			"
	::= { txConfigItems 43 }

txAcm128aryHysteresis OBJECT-TYPE
	SYNTAX		Unsigned32
	UNITS		"0.01 dB"
	MAX-ACCESS	read-write
	STATUS		current
	DESCRIPTION "Tx ACM 128-ary Hysteresis
			Oid=1.3.6.1.4.1.31968.3.1.4.1.9.44
			"
	::= { txConfigItems 44 }

txAcm256aryHysteresis OBJECT-TYPE
	SYNTAX		Unsigned32
	UNITS		"0.01 dB"
	MAX-ACCESS	read-write
	STATUS		current
	DESCRIPTION "Tx ACM 256-ary Hysteresis
			Oid=1.3.6.1.4.1.31968.3.1.4.1.9.45
			"
	::= { txConfigItems 45 }

txAcmMargin OBJECT-TYPE
	SYNTAX		Unsigned32
	UNITS		"0.01 dB"
	MAX-ACCESS	read-write
	STATUS		current
	DESCRIPTION "Tx ACM Margin - ACR Margin
			Oid=1.3.6.1.4.1.31968.3.1.4.1.9.46
			"
	::= { txConfigItems 46 }

txTransecOperation OBJECT-TYPE
	SYNTAX		INTEGER {
		encryptionOff(0),
		encryptionOn(1),
		generateRandomKey(2),
		zeroizeTxKey(10)
	}
	MAX-ACCESS	read-write
	STATUS		current
	DESCRIPTION "Tx Operation, where:
			    0) 'Encryption Off'
			    1) 'Encryption On'
			    2) 'Generate Random Key'
			    10) 'Zeroize Tx Key'
			Oid=1.3.6.1.4.1.31968.3.1.4.1.9.47
			"
	::= { txConfigItems 47 }

txTransecKeySize OBJECT-TYPE
	SYNTAX		INTEGER {
		aes128(0),
		aes192(1),
		aes256(2)
	}
	MAX-ACCESS	read-write
	STATUS		current
	DESCRIPTION "Tx Key Size, where:
			    0) 'AES-128'
			    1) 'AES-192'
			    2) 'AES-256'
			Oid=1.3.6.1.4.1.31968.3.1.4.1.9.48
			"
	::= { txConfigItems 48 }

txTransecKeyRoll OBJECT-TYPE
	SYNTAX		INTEGER {
		idle(0),
		requestKeyRoll(1)
	}
	MAX-ACCESS	read-write
	STATUS		current
	DESCRIPTION "Tx Manual Key Roll, where:
			    0) 'Idle'
			    1) 'Request Key Roll'
			Oid=1.3.6.1.4.1.31968.3.1.4.1.9.49
			"
	::= { txConfigItems 49 }

txTransecKey OBJECT-TYPE
	SYNTAX		DisplayString(SIZE(0..64))
	MAX-ACCESS	read-write
	STATUS		current
	DESCRIPTION "Tx Key
			Oid=1.3.6.1.4.1.31968.3.1.4.1.9.50
			"
	::= { txConfigItems 50 }

txTransecKeyHash OBJECT-TYPE
	SYNTAX		DisplayString(SIZE(0..64))
	MAX-ACCESS	read-only
	STATUS		current
	DESCRIPTION "Tx Key Hash (SHA3-256)
			Oid=1.3.6.1.4.1.31968.3.1.4.1.9.51
			"
	::= { txConfigItems 51 }

txTransecAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Tx TRANSEC Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.9.52
			"
	::= { txConfigItems 52 }

txTransecEvent OBJECT-TYPE
	SYNTAX		INTEGER {
		doNotLog(0),
		log(1),
		logAndSendAlert(2),
		logAndSendAlertNowNoDebounce(3)
	}
	MAX-ACCESS	read-write
	STATUS		current
	DESCRIPTION "Tx TRANSEC Event, where:
			    0) 'Do Not Log'
			    1) 'Log'
			    2) 'Log & Send Alert'
			    3) 'Log & Send Alert Now (No Debounce)'
			Oid=1.3.6.1.4.1.31968.3.1.4.1.9.53
			"
	::= { txConfigItems 53 }

txCalPowerMeterIp OBJECT-TYPE
	SYNTAX		IpAddress
	MAX-ACCESS	read-write
	STATUS		current
	DESCRIPTION "Tx RF Power Meter IP Address
			Oid=1.3.6.1.4.1.31968.3.1.4.1.9.54
			"
	::= { txConfigItems 54 }

txCalPowerMeterPort OBJECT-TYPE
	SYNTAX		Unsigned32
	UNITS		"1"
	MAX-ACCESS	read-write
	STATUS		current
	DESCRIPTION "Tx RF Power Meter Port Number
			Oid=1.3.6.1.4.1.31968.3.1.4.1.9.55
			"
	::= { txConfigItems 55 }

txAupcAlarm OBJECT-TYPE
	SYNTAX		INTEGER {
		off(0),
		report(1),
		alarm(3),
		alarmAndRelayOutput(5)
	}
	MAX-ACCESS	read-write
	STATUS		current
	DESCRIPTION "Tx AUPC Alarm, where:
			    0) 'Off'
			    1) 'Report'
			    3) 'Alarm'
			    5) 'Alarm & Relay Output'
			Oid=1.3.6.1.4.1.31968.3.1.4.1.9.56
			"
	::= { txConfigItems 56 }

txGseDataProtocol OBJECT-TYPE
	SYNTAX		INTEGER {
		gseDvb(0),
		gseLowOverhead(1),
		gseCt(2),
		gseCt2(3),
		gseDvbM7(4)
	}
	MAX-ACCESS	read-write
	STATUS		current
	DESCRIPTION "Tx Protocol, where:
			    0) 'GSE DVB'
			    1) 'GSE Low Overhead'
			    2) 'GSE CT'
			    3) 'GSE CT2'
			    4) 'GSE DVB (M7)'
			Oid=1.3.6.1.4.1.31968.3.1.4.1.9.57
			"
	::= { txConfigItems 57 }

txHdlcDataProtocol OBJECT-TYPE
	SYNTAX		INTEGER {
		m500Hdlc(0),
		m7Hdlc(1),
		m7HdlcHoe(2)
	}
	MAX-ACCESS	read-write
	STATUS		current
	DESCRIPTION "Tx Protocol, where:
			    0) 'M500 HDLC'
			    1) 'M7 HDLC'
			    2) 'M7 HDLC HoE'
			Oid=1.3.6.1.4.1.31968.3.1.4.1.9.58
			"
	::= { txConfigItems 58 }

txDataIdle OBJECT-TYPE
	SYNTAX		INTEGER {
		off(0),
		on(1)
	}
	MAX-ACCESS	read-write
	STATUS		current
	DESCRIPTION "Tx Idle Packets, where:
			    0) 'Off'
			    1) 'On'
			Oid=1.3.6.1.4.1.31968.3.1.4.1.9.59
			"
	::= { txConfigItems 59 }

txDataMcc OBJECT-TYPE
	SYNTAX		INTEGER {
		off(0),
		on(1)
	}
	MAX-ACCESS	read-write
	STATUS		current
	DESCRIPTION "Tx MCC/ACM/ACR Packets, where:
			    0) 'Off'
			    1) 'On'
			Oid=1.3.6.1.4.1.31968.3.1.4.1.9.60
			"
	::= { txConfigItems 60 }

txDataHoeSmac OBJECT-TYPE
	SYNTAX		PhysAddress
	MAX-ACCESS	read-write
	STATUS		current
	DESCRIPTION "Tx HoE SMAC Address
			Oid=1.3.6.1.4.1.31968.3.1.4.1.9.61
			"
	::= { txConfigItems 61 }

txDataHoeDmac OBJECT-TYPE
	SYNTAX		PhysAddress
	MAX-ACCESS	read-write
	STATUS		current
	DESCRIPTION "Tx HoE DMAC Address
			Oid=1.3.6.1.4.1.31968.3.1.4.1.9.62
			"
	::= { txConfigItems 62 }

txQosMode OBJECT-TYPE
	SYNTAX		INTEGER {
		off(0),
		strictPriority(1),
		wred(2),
		custom(3)
	}
	MAX-ACCESS	read-write
	STATUS		current
	DESCRIPTION "Tx QoS Mode, where:
			    0) 'Off'
			    1) 'Strict Priority'
			    2) 'WRED'
			    3) 'Custom'
			Oid=1.3.6.1.4.1.31968.3.1.4.1.9.63
			"
	::= { txConfigItems 63 }

txQosLive OBJECT-TYPE
	SYNTAX		Unsigned32
	UNITS		"0.01 ms"
	MAX-ACCESS	read-write
	STATUS		current
	DESCRIPTION "Tx QoS Live Time
			Oid=1.3.6.1.4.1.31968.3.1.4.1.9.64
			"
	::= { txConfigItems 64 }

txQos1st OBJECT-TYPE
	SYNTAX		INTEGER {
		none(0),
		ipv4DscpIpv6Tc(1),
		vlanPcp(2),
		vlanIdUsingId3Msb(3),
		mplsExp(4),
		mplsExpUsingIpOnly(5)
	}
	MAX-ACCESS	read-write
	STATUS		current
	DESCRIPTION "Tx QoS 1st Priority, where:
			    0) 'None'
			    1) 'IPv4-DSCP/IPv6-TC'
			    2) 'VLAN-PCP'
			    3) 'VLAN-ID Using ID 3 MSb'
			    4) 'MPLS-EXP'
			    5) 'MPLS-EXP Using IP Only'
			Oid=1.3.6.1.4.1.31968.3.1.4.1.9.65
			"
	::= { txConfigItems 65 }

txQos2nd OBJECT-TYPE
	SYNTAX		INTEGER {
		none(0),
		ipv4DscpIpv6Tc(1),
		vlanPcp(2),
		vlanIdUsingId3Msb(3),
		mplsExp(4),
		mplsExpUsingIpOnly(5)
	}
	MAX-ACCESS	read-write
	STATUS		current
	DESCRIPTION "Tx QoS 2nd Priority, where:
			    0) 'None'
			    1) 'IPv4-DSCP/IPv6-TC'
			    2) 'VLAN-PCP'
			    3) 'VLAN-ID Using ID 3 MSb'
			    4) 'MPLS-EXP'
			    5) 'MPLS-EXP Using IP Only'
			Oid=1.3.6.1.4.1.31968.3.1.4.1.9.66
			"
	::= { txConfigItems 66 }

txQos3rd OBJECT-TYPE
	SYNTAX		INTEGER {
		none(0),
		ipv4DscpIpv6Tc(1),
		vlanPcp(2),
		vlanIdUsingId3Msb(3),
		mplsExp(4),
		mplsExpUsingIpOnly(5)
	}
	MAX-ACCESS	read-write
	STATUS		current
	DESCRIPTION "Tx QoS 3rd Priority, where:
			    0) 'None'
			    1) 'IPv4-DSCP/IPv6-TC'
			    2) 'VLAN-PCP'
			    3) 'VLAN-ID Using ID 3 MSb'
			    4) 'MPLS-EXP'
			    5) 'MPLS-EXP Using IP Only'
			Oid=1.3.6.1.4.1.31968.3.1.4.1.9.67
			"
	::= { txConfigItems 67 }

txQosDefault OBJECT-TYPE
	SYNTAX		Unsigned32
	UNITS		"1"
	MAX-ACCESS	read-write
	STATUS		current
	DESCRIPTION "Tx QoS Default Priority
			Oid=1.3.6.1.4.1.31968.3.1.4.1.9.68
			"
	::= { txConfigItems 68 }

txQueue7Weight OBJECT-TYPE
	SYNTAX		Unsigned32
	UNITS		"1"
	MAX-ACCESS	read-write
	STATUS		current
	DESCRIPTION "Tx QoS Queue 7 Weight,
			    0=Off
			Oid=1.3.6.1.4.1.31968.3.1.4.1.9.69
			"
	::= { txConfigItems 69 }

txQueue7Live OBJECT-TYPE
	SYNTAX		Unsigned32
	UNITS		"0.01 ms"
	MAX-ACCESS	read-write
	STATUS		current
	DESCRIPTION "Tx QoS Queue 7 Live Time
			Oid=1.3.6.1.4.1.31968.3.1.4.1.9.70
			"
	::= { txConfigItems 70 }

txQueue6Weight OBJECT-TYPE
	SYNTAX		Unsigned32
	UNITS		"1"
	MAX-ACCESS	read-write
	STATUS		current
	DESCRIPTION "Tx QoS Queue 6 Weight,
			    0=Off
			Oid=1.3.6.1.4.1.31968.3.1.4.1.9.71
			"
	::= { txConfigItems 71 }

txQueue6Live OBJECT-TYPE
	SYNTAX		Unsigned32
	UNITS		"0.01 ms"
	MAX-ACCESS	read-write
	STATUS		current
	DESCRIPTION "Tx QoS Queue 6 Live Time
			Oid=1.3.6.1.4.1.31968.3.1.4.1.9.72
			"
	::= { txConfigItems 72 }

txQueue5Weight OBJECT-TYPE
	SYNTAX		Unsigned32
	UNITS		"1"
	MAX-ACCESS	read-write
	STATUS		current
	DESCRIPTION "Tx QoS Queue 5 Weight,
			    0=Off
			Oid=1.3.6.1.4.1.31968.3.1.4.1.9.73
			"
	::= { txConfigItems 73 }

txQueue5Live OBJECT-TYPE
	SYNTAX		Unsigned32
	UNITS		"0.01 ms"
	MAX-ACCESS	read-write
	STATUS		current
	DESCRIPTION "Tx QoS Queue 5 Live Time
			Oid=1.3.6.1.4.1.31968.3.1.4.1.9.74
			"
	::= { txConfigItems 74 }

txQueue4Weight OBJECT-TYPE
	SYNTAX		Unsigned32
	UNITS		"1"
	MAX-ACCESS	read-write
	STATUS		current
	DESCRIPTION "Tx QoS Queue 4 Weight,
			    0=Off
			Oid=1.3.6.1.4.1.31968.3.1.4.1.9.75
			"
	::= { txConfigItems 75 }

txQueue4Live OBJECT-TYPE
	SYNTAX		Unsigned32
	UNITS		"0.01 ms"
	MAX-ACCESS	read-write
	STATUS		current
	DESCRIPTION "Tx QoS Queue 4 Live Time
			Oid=1.3.6.1.4.1.31968.3.1.4.1.9.76
			"
	::= { txConfigItems 76 }

txQueue3Weight OBJECT-TYPE
	SYNTAX		Unsigned32
	UNITS		"1"
	MAX-ACCESS	read-write
	STATUS		current
	DESCRIPTION "Tx QoS Queue 3 Weight,
			    0=Off
			Oid=1.3.6.1.4.1.31968.3.1.4.1.9.77
			"
	::= { txConfigItems 77 }

txQueue3Live OBJECT-TYPE
	SYNTAX		Unsigned32
	UNITS		"0.01 ms"
	MAX-ACCESS	read-write
	STATUS		current
	DESCRIPTION "Tx QoS Queue 3 Live Time
			Oid=1.3.6.1.4.1.31968.3.1.4.1.9.78
			"
	::= { txConfigItems 78 }

txQueue2Weight OBJECT-TYPE
	SYNTAX		Unsigned32
	UNITS		"1"
	MAX-ACCESS	read-write
	STATUS		current
	DESCRIPTION "Tx QoS Queue 2 Weight,
			    0=Off
			Oid=1.3.6.1.4.1.31968.3.1.4.1.9.79
			"
	::= { txConfigItems 79 }

txQueue2Live OBJECT-TYPE
	SYNTAX		Unsigned32
	UNITS		"0.01 ms"
	MAX-ACCESS	read-write
	STATUS		current
	DESCRIPTION "Tx QoS Queue 2 Live Time
			Oid=1.3.6.1.4.1.31968.3.1.4.1.9.80
			"
	::= { txConfigItems 80 }

txQueue1Weight OBJECT-TYPE
	SYNTAX		Unsigned32
	UNITS		"1"
	MAX-ACCESS	read-write
	STATUS		current
	DESCRIPTION "Tx QoS Queue 1 Weight,
			    0=Off
			Oid=1.3.6.1.4.1.31968.3.1.4.1.9.81
			"
	::= { txConfigItems 81 }

txQueue1Live OBJECT-TYPE
	SYNTAX		Unsigned32
	UNITS		"0.01 ms"
	MAX-ACCESS	read-write
	STATUS		current
	DESCRIPTION "Tx QoS Queue 1 Live Time
			Oid=1.3.6.1.4.1.31968.3.1.4.1.9.82
			"
	::= { txConfigItems 82 }

txQueue0Weight OBJECT-TYPE
	SYNTAX		Unsigned32
	UNITS		"1"
	MAX-ACCESS	read-write
	STATUS		current
	DESCRIPTION "Tx QoS Queue 0 Weight,
			    0=Off
			Oid=1.3.6.1.4.1.31968.3.1.4.1.9.83
			"
	::= { txConfigItems 83 }

txQueue0Live OBJECT-TYPE
	SYNTAX		Unsigned32
	UNITS		"0.01 ms"
	MAX-ACCESS	read-write
	STATUS		current
	DESCRIPTION "Tx QoS Queue 0 Live Time
			Oid=1.3.6.1.4.1.31968.3.1.4.1.9.84
			"
	::= { txConfigItems 84 }

txMccProtocol OBJECT-TYPE
	SYNTAX		INTEGER {
		m7BinaryPacket(0),
		m7xcBinaryPacket(1)
	}
	MAX-ACCESS	read-write
	STATUS		current
	DESCRIPTION "Tx MCC Protocol, where:
			    0) 'M7 Binary Packet'
			    1) 'M7XC Binary Packet'
			Oid=1.3.6.1.4.1.31968.3.1.4.1.9.85
			"
	::= { txConfigItems 85 }

txDvbMccRate OBJECT-TYPE
	SYNTAX		Unsigned32
	UNITS		"1 bps"
	MAX-ACCESS	read-write
	STATUS		current
	DESCRIPTION "Tx MCC Rate Limit
			Oid=1.3.6.1.4.1.31968.3.1.4.1.9.86
			"
	::= { txConfigItems 86 }

txLdpcMccRate OBJECT-TYPE
	SYNTAX		Unsigned32
	UNITS		"1 bps"
	MAX-ACCESS	read-write
	STATUS		current
	DESCRIPTION "Tx MCC Rate Limit
			Oid=1.3.6.1.4.1.31968.3.1.4.1.9.87
			"
	::= { txConfigItems 87 }

txMccAddress OBJECT-TYPE
	SYNTAX		Unsigned32
	UNITS		"1"
	MAX-ACCESS	read-write
	STATUS		current
	DESCRIPTION "Tx MCC Address,
			    255=Global
			Oid=1.3.6.1.4.1.31968.3.1.4.1.9.88
			"
	::= { txConfigItems 88 }

txAcmModcodEvent OBJECT-TYPE
	SYNTAX		INTEGER {
		doNotLog(0),
		log(1),
		logAndSendAlert(2),
		logAndSendAlertNowNoDebounce(3)
	}
	MAX-ACCESS	read-write
	STATUS		current
	DESCRIPTION "Tx ACM ModCod Event - ACR ModCod Event, where:
			    0) 'Do Not Log'
			    1) 'Log'
			    2) 'Log & Send Alert'
			    3) 'Log & Send Alert Now (No Debounce)'
			Oid=1.3.6.1.4.1.31968.3.1.4.1.9.91
			"
	::= { txConfigItems 91 }

txDataInactive OBJECT-TYPE
	SYNTAX		Unsigned32
	UNITS		"s"
	MAX-ACCESS	read-write
	STATUS		current
	DESCRIPTION "Tx Data Inactive Time
			Oid=1.3.6.1.4.1.31968.3.1.4.1.9.92
			"
	::= { txConfigItems 92 }

txDataAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Tx Data Inactive Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.9.93
			"
	::= { txConfigItems 93 }

txCarrierEvent OBJECT-TYPE
	SYNTAX		INTEGER {
		doNotLog(0),
		log(1),
		logAndSendAlert(2),
		logAndSendAlertNowNoDebounce(3)
	}
	MAX-ACCESS	read-write
	STATUS		current
	DESCRIPTION "Tx Carrier Event, where:
			    0) 'Do Not Log'
			    1) 'Log'
			    2) 'Log & Send Alert'
			    3) 'Log & Send Alert Now (No Debounce)'
			Oid=1.3.6.1.4.1.31968.3.1.4.1.9.94
			"
	::= { txConfigItems 94 }

txAupcEvent OBJECT-TYPE
	SYNTAX		INTEGER {
		doNotLog(0),
		log(1),
		logAndSendAlert(2),
		logAndSendAlertNowNoDebounce(3)
	}
	MAX-ACCESS	read-write
	STATUS		current
	DESCRIPTION "Tx AUPC Alarm Event, where:
			    0) 'Do Not Log'
			    1) 'Log'
			    2) 'Log & Send Alert'
			    3) 'Log & Send Alert Now (No Debounce)'
			Oid=1.3.6.1.4.1.31968.3.1.4.1.9.95
			"
	::= { txConfigItems 95 }

txMccChannelEvent OBJECT-TYPE
	SYNTAX		INTEGER {
		doNotLog(0),
		log(1),
		logAndSendAlert(2),
		logAndSendAlertNowNoDebounce(3)
	}
	MAX-ACCESS	read-write
	STATUS		current
	DESCRIPTION "Tx MCC Remote Channel Alarm Event, where:
			    0) 'Do Not Log'
			    1) 'Log'
			    2) 'Log & Send Alert'
			    3) 'Log & Send Alert Now (No Debounce)'
			Oid=1.3.6.1.4.1.31968.3.1.4.1.9.96
			"
	::= { txConfigItems 96 }

txAcmLowEsn0Event OBJECT-TYPE
	SYNTAX		INTEGER {
		doNotLog(0),
		log(1),
		logAndSendAlert(2),
		logAndSendAlertNowNoDebounce(3)
	}
	MAX-ACCESS	read-write
	STATUS		current
	DESCRIPTION "Tx ACM Low Es/N0 Alarm Event - ACR Low SNR Alarm Event, where:
			    0) 'Do Not Log'
			    1) 'Log'
			    2) 'Log & Send Alert'
			    3) 'Log & Send Alert Now (No Debounce)'
			Oid=1.3.6.1.4.1.31968.3.1.4.1.9.97
			"
	::= { txConfigItems 97 }

txDataEvent OBJECT-TYPE
	SYNTAX		INTEGER {
		doNotLog(0),
		log(1),
		logAndSendAlert(2),
		logAndSendAlertNowNoDebounce(3)
	}
	MAX-ACCESS	read-write
	STATUS		current
	DESCRIPTION "Tx Data Inactivity Alarm Event, where:
			    0) 'Do Not Log'
			    1) 'Log'
			    2) 'Log & Send Alert'
			    3) 'Log & Send Alert Now (No Debounce)'
			Oid=1.3.6.1.4.1.31968.3.1.4.1.9.98
			"
	::= { txConfigItems 98 }

txRfOutput OBJECT-TYPE
	SYNTAX		INTEGER {
		off(0),
		on(1)
	}
	MAX-ACCESS	read-write
	STATUS		current
	DESCRIPTION "Tx Master RF Output, where:
			    0) 'Off'
			    1) 'On'
			Oid=1.3.6.1.4.1.31968.3.1.4.1.9.101
			"
	::= { txConfigItems 101 }

txCalTask OBJECT-TYPE
	SYNTAX		INTEGER {
		idle(0),
		runLevelCal(1),
		runIAndQAndTiltCal(2),
		runIAndQCal(3),
		runTiltCal(4)
	}
	MAX-ACCESS	read-write
	STATUS		current
	DESCRIPTION "Tx Calibration Task, where:
			    0) 'Idle'
			    1) 'Run Level Cal'
			    2) 'Run I & Q And Tilt Cal'
			    3) 'Run I & Q Cal'
			    4) 'Run Tilt Cal'
			Oid=1.3.6.1.4.1.31968.3.1.4.1.9.102
			"
	::= { txConfigItems 102 }

txCarrierAlarm OBJECT-TYPE
	SYNTAX		INTEGER {
		alarmAndMuteTxOutput(4),
		alarmAndRelayOutputAndMuteTxOutput(6)
	}
	MAX-ACCESS	read-write
	STATUS		current
	DESCRIPTION "Tx Carrier Alarm, where:
			    4) 'Alarm & Mute Tx Output'
			    6) 'Alarm & Relay Output & Mute Tx Output'
			Oid=1.3.6.1.4.1.31968.3.1.4.1.9.112
			"
	::= { txConfigItems 112 }

txDsssChipRate OBJECT-TYPE
	SYNTAX		Unsigned32
	MAX-ACCESS	read-write
	STATUS		current
	DESCRIPTION "Tx DSSS Chip Rate
			Oid=1.3.6.1.4.1.31968.3.1.4.1.9.113
			"
	::= { txConfigItems 113 }

txDsssSpreadFactor OBJECT-TYPE
	SYNTAX		Unsigned32
	UNITS		"1"
	MAX-ACCESS	read-write
	STATUS		current
	DESCRIPTION "Tx DSSS Spread Factor
			Oid=1.3.6.1.4.1.31968.3.1.4.1.9.114
			"
	::= { txConfigItems 114 }

txDsssCodeLength OBJECT-TYPE
	SYNTAX		INTEGER {
		n511(0),
		n4095SlowAcquisition(1)
	}
	MAX-ACCESS	read-write
	STATUS		current
	DESCRIPTION "Tx DSSS Code Sequence Length, where:
			    0) '511'
			    1) '4095 (Slow Acquisition)'
			Oid=1.3.6.1.4.1.31968.3.1.4.1.9.115
			"
	::= { txConfigItems 115 }

txDsssCode OBJECT-TYPE
	SYNTAX		Unsigned32
	UNITS		"1"
	MAX-ACCESS	read-write
	STATUS		current
	DESCRIPTION "Tx DSSS Code Index
			Oid=1.3.6.1.4.1.31968.3.1.4.1.9.116
			"
	::= { txConfigItems 116 }

txDsssService OBJECT-TYPE
	SYNTAX		INTEGER {
		ldpcGen2(0),
		ldpcGen2Acr(1)
	}
	MAX-ACCESS	read-write
	STATUS		current
	DESCRIPTION "Tx Service, where:
			    0) 'LDPC-Gen2'
			    1) 'LDPC-Gen2 ACR'
			Oid=1.3.6.1.4.1.31968.3.1.4.1.9.117
			"
	::= { txConfigItems 117 }

txDsssFixedModcod OBJECT-TYPE
	SYNTAX		INTEGER {
		bpsk1x2(0),
		bpsk8x15(1),
		bpsk4x7(2),
		bpsk8x13(3),
		bpsk2x3(4),
		bpsk16x23(5),
		bpsk8x11(6),
		bpsk16x21(7),
		bpsk4x5(8),
		bpsk16x19(9),
		bpsk8x9(10)
	}
	MAX-ACCESS	read-write
	STATUS		current
	DESCRIPTION "Tx ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'BPSK 16/21'
			    8) 'BPSK 4/5'
			    9) 'BPSK 16/19'
			    10) 'BPSK 8/9'
			Oid=1.3.6.1.4.1.31968.3.1.4.1.9.118
			"
	::= { txConfigItems 118 }

txAcrLowSnrLimit OBJECT-TYPE
	SYNTAX		Integer32
	UNITS		"0.01 dB"
	MAX-ACCESS	read-write
	STATUS		current
	DESCRIPTION "Tx ACR Low SNR Limit
			Oid=1.3.6.1.4.1.31968.3.1.4.1.9.119
			"
	::= { txConfigItems 119 }

txVcmDesiredDrainTime OBJECT-TYPE
	SYNTAX		Unsigned32
	MAX-ACCESS	read-write
	STATUS		current
	DESCRIPTION "Tx Desired Drain Time
			Oid=1.3.6.1.4.1.31968.3.1.4.1.9.120
			"
	::= { txConfigItems 120 }

txVcmQueueLiveTime OBJECT-TYPE
	SYNTAX		Unsigned32
	MAX-ACCESS	read-write
	STATUS		current
	DESCRIPTION "Tx Queue Live Time
			Oid=1.3.6.1.4.1.31968.3.1.4.1.9.121
			"
	::= { txConfigItems 121 }

txVcmCirMaxAlarm OBJECT-TYPE
	SYNTAX		INTEGER {
		off(0),
		report(1),
		alarm(3),
		alarmAndRelayOutput(5)
	}
	MAX-ACCESS	read-write
	STATUS		current
	DESCRIPTION "Tx CIR Maximum Limit Alarm, where:
			    0) 'Off'
			    1) 'Report'
			    3) 'Alarm'
			    5) 'Alarm & Relay Output'
			Oid=1.3.6.1.4.1.31968.3.1.4.1.9.122
			"
	::= { txConfigItems 122 }

txVcmCirMaxEvent OBJECT-TYPE
	SYNTAX		INTEGER {
		doNotLog(0),
		log(1),
		logAndSendAlert(2),
		logAndSendAlertNowNoDebounce(3)
	}
	MAX-ACCESS	read-write
	STATUS		current
	DESCRIPTION "Tx CIR Maximum Limit Alarm Event, where:
			    0) 'Do Not Log'
			    1) 'Log'
			    2) 'Log & Send Alert'
			    3) 'Log & Send Alert Now (No Debounce)'
			Oid=1.3.6.1.4.1.31968.3.1.4.1.9.123
			"
	::= { txConfigItems 123 }

txHdrFixedModcod OBJECT-TYPE
	SYNTAX		INTEGER {
		fr80t5x4L8(0),
		fr80t5x4L7(1),
		fr80t5x4L6(2),
		fr80t5x4L5(3),
		fr80t5x4L4(4),
		fr80t5x4L3(5),
		fr80t5x4L2(6),
		fr80t5x4L1(7),
		fr80t5x16L3(8),
		fr80t5x16L2(9),
		fr80t5x16L1(10),
		fr80t5x16R(11),
		fr80t5x16H1(12),
		fr80t5x16H2(13),
		fr80t5x16H3(14),
		fr80t5x16H4(15),
		fr80t5x16H5(16),
		fr80t5x16H6(17),
		fr80t5x32H1(18),
		fr80t5x32H2(19),
		fr80t5x32H3(20),
		fr80t5x32H4(21),
		fr80t5x32H5(22),
		fr80t5x32H6(23),
		fr80t5x64R(24),
		fr80t5x64H1(25),
		fr80t5x64H2(26),
		fr80t5x64H3(27),
		fr80t5x64H4(28),
		fr80t5x64H5(29),
		fr80t5x64H6(30)
	}
	MAX-ACCESS	read-write
	STATUS		current
	DESCRIPTION "Tx ModCod, where:
			    0) 'FR80T5X4-L8'
			    1) 'FR80T5X4-L7'
			    2) 'FR80T5X4-L6'
			    3) 'FR80T5X4-L5'
			    4) 'FR80T5X4-L4'
			    5) 'FR80T5X4-L3'
			    6) 'FR80T5X4-L2'
			    7) 'FR80T5X4-L1'
			    8) 'FR80T5X16-L3'
			    9) 'FR80T5X16-L2'
			    10) 'FR80T5X16-L1'
			    11) 'FR80T5X16-R'
			    12) 'FR80T5X16-H1'
			    13) 'FR80T5X16-H2'
			    14) 'FR80T5X16-H3'
			    15) 'FR80T5X16-H4'
			    16) 'FR80T5X16-H5'
			    17) 'FR80T5X16-H6'
			    18) 'FR80T5X32-H1'
			    19) 'FR80T5X32-H2'
			    20) 'FR80T5X32-H3'
			    21) 'FR80T5X32-H4'
			    22) 'FR80T5X32-H5'
			    23) 'FR80T5X32-H6'
			    24) 'FR80T5X64-R'
			    25) 'FR80T5X64-H1'
			    26) 'FR80T5X64-H2'
			    27) 'FR80T5X64-H3'
			    28) 'FR80T5X64-H4'
			    29) 'FR80T5X64-H5'
			    30) 'FR80T5X64-H6'
			Oid=1.3.6.1.4.1.31968.3.1.4.1.9.124
			"
	::= { txConfigItems 124 }

txHdrSymbolRate OBJECT-TYPE
	SYNTAX		Unsigned32
	UNITS		"1 sps"
	MAX-ACCESS	read-write
	STATUS		current
	DESCRIPTION "Tx Symbol Rate
			Oid=1.3.6.1.4.1.31968.3.1.4.1.9.125
			"
	::= { txConfigItems 125 }

txHdrTotalMinSymbolRate OBJECT-TYPE
	SYNTAX		Unsigned32
	UNITS		"1 sps"
	MAX-ACCESS	read-write
	STATUS		current
	DESCRIPTION "Tx Total Min Symbol Rate
			Oid=1.3.6.1.4.1.31968.3.1.4.1.9.126
			"
	::= { txConfigItems 126 }

txHdrTotalMaxSymbolRate OBJECT-TYPE
	SYNTAX		Unsigned32
	UNITS		"1 sps"
	MAX-ACCESS	read-write
	STATUS		current
	DESCRIPTION "Tx Total Max Symbol Rate
			Oid=1.3.6.1.4.1.31968.3.1.4.1.9.127
			"
	::= { txConfigItems 127 }

txLevelMode OBJECT-TYPE
	SYNTAX		INTEGER {
		constantPower(0),
		constantPsd(1)
	}
	MAX-ACCESS	read-write
	STATUS		current
	DESCRIPTION "Tx Output Level Mode, where:
			    0) 'Constant Power'
			    1) 'Constant PSD'
			Oid=1.3.6.1.4.1.31968.3.1.4.1.9.128
			"
	::= { txConfigItems 128 }

txConfigTable OBJECT-TYPE
	SYNTAX		SEQUENCE OF TxConfigEntry
	MAX-ACCESS	not-accessible
	STATUS		current
	DESCRIPTION "Tx Config Channel Table
			Oid=1.3.6.1.4.1.31968.3.1.4.1.10
			"
	::= { m7xcModemObjs 10 }

txConfigEntry OBJECT-TYPE
	SYNTAX		TxConfigEntry
	MAX-ACCESS	not-accessible
	STATUS		current
	DESCRIPTION "Tx Config Channel Entry
			Oid=1.3.6.1.4.1.31968.3.1.4.1.10.1
			"
	INDEX {
		txConfigIndex
	}
	::= { txConfigTable 1 }

TxConfigEntry ::=
	SEQUENCE {
		txConfigIndex           Unsigned32,
		txBucFrequency          DisplayString,
		txFrequency             Unsigned32,
		txLevelOffset           Integer32,
		txOutput                INTEGER,
		txTestModulation        INTEGER,
		txSymbolRate            Unsigned32,
		txVcmService            INTEGER,
		txVcmVlanId             Unsigned32,
		txVcmRxChannel          Unsigned32,
		txVcmCirMode            INTEGER,
		txVcmDesiredCir         Unsigned32,
		txVcmMir                Unsigned32,
		txVcmMinEsn0            Integer32,
		txVcmMaxEsn0            Integer32,
		txVcmFixedModcod        INTEGER,
		txVcmMinModcodAlarm     INTEGER,
		txVcmLowEsn0Alarm       INTEGER,
		txVcmLowEsn0Limit       Integer32,
		txVcmMccChannelAlarm    INTEGER,
		txVcmDataAlarm          INTEGER,
		txVcmDataInactive       Unsigned32,
		txVcmMccChannelEvent    INTEGER,
		txVcmMinModcodEvent     INTEGER,
		txVcmLowEsn0Event       INTEGER,
		txVcmDataEvent          INTEGER,
		txVcmId                 DisplayString
	}

txConfigIndex OBJECT-TYPE
	SYNTAX		Unsigned32(1..16)
	MAX-ACCESS	not-accessible
	STATUS		current
	DESCRIPTION "Tx Config Channel Index
			Oid=1.3.6.1.4.1.31968.3.1.4.1.10.1.1
			"
	::= { txConfigEntry 1 }

txBucFrequency OBJECT-TYPE
	SYNTAX		DisplayString(SIZE(1..24))
	UNITS		"1 Hz"
	MAX-ACCESS	read-write
	STATUS		current
	DESCRIPTION "Tx BUC Carrier Frequency,
			    Text Number, Decimal
			Oid=1.3.6.1.4.1.31968.3.1.4.1.10.1.2
			"
	::= { txConfigEntry 2 }

txFrequency OBJECT-TYPE
	SYNTAX		Unsigned32
	UNITS		"1 Hz"
	MAX-ACCESS	read-write
	STATUS		current
	DESCRIPTION "Tx Carrier Frequency
			Oid=1.3.6.1.4.1.31968.3.1.4.1.10.1.3
			"
	::= { txConfigEntry 3 }

txLevelOffset OBJECT-TYPE
	SYNTAX		Integer32
	UNITS		"0.01 dB"
	MAX-ACCESS	read-write
	STATUS		current
	DESCRIPTION "Tx Carrier Level Offset
			Oid=1.3.6.1.4.1.31968.3.1.4.1.10.1.4
			"
	::= { txConfigEntry 4 }

txOutput OBJECT-TYPE
	SYNTAX		INTEGER {
		off(0),
		on(1),
		onDataIdle(2),
		onDataLive(3),
		onDataDown(4),
		onDataPendingToGoDown(5),
		onDataPendingToGoUp(6),
		onDataUp(7),
		allPendingToCurrentAndNotifyRx(8)
	}
	MAX-ACCESS	read-write
	STATUS		current
	DESCRIPTION "Tx Output, where:
			    0) 'Off'
			    1) 'On'
			    2) 'On, Data Idle'
			    3) 'On, Data Live'
			    4) 'On, Data Down'
			    5) 'On, Data Pending To Go Down'
			    6) 'On, Data Pending To Go Up'
			    7) 'On, Data Up'
			    8) 'All Pending To Current & Notify Rx'
			Oid=1.3.6.1.4.1.31968.3.1.4.1.10.1.5
			"
	::= { txConfigEntry 5 }

txTestModulation OBJECT-TYPE
	SYNTAX		INTEGER {
		off(0),
		pureCxr(1),
		alt10(2),
		lowerSideband(3),
		upperSideband(4),
		qpskPnSequence(5)
	}
	MAX-ACCESS	read-write
	STATUS		current
	DESCRIPTION "Tx Test Modulation, where:
			    0) 'Off'
			    1) 'Pure CXR'
			    2) 'Alt 1/0'
			    3) 'Lower Sideband'
			    4) 'Upper Sideband'
			    5) 'QPSK PN Sequence'
			Oid=1.3.6.1.4.1.31968.3.1.4.1.10.1.6
			"
	::= { txConfigEntry 6 }

txSymbolRate OBJECT-TYPE
	SYNTAX		Unsigned32
	UNITS		"1 sps"
	MAX-ACCESS	read-write
	STATUS		current
	DESCRIPTION "Tx Symbol Rate
			Oid=1.3.6.1.4.1.31968.3.1.4.1.10.1.7
			"
	::= { txConfigEntry 7 }

txVcmService OBJECT-TYPE
	SYNTAX		INTEGER {
		off(0),
		dvbS2x(1),
		dvbS2xAcmPreferred(2),
		dvbS2xAcmPreferredL(3),
		broadcastToAllDestinations(4)
	}
	MAX-ACCESS	read-write
	STATUS		current
	DESCRIPTION "Tx Queue Service, where:
			    0) 'Off'
			    1) 'DVB-S2X'
			    2) 'DVB-S2X ACM Preferred'
			    3) 'DVB-S2X ACM Preferred-L'
			    4) 'Broadcast To All Destinations'
			Oid=1.3.6.1.4.1.31968.3.1.4.1.10.1.8
			"
	::= { txConfigEntry 8 }

txVcmVlanId OBJECT-TYPE
	SYNTAX		Unsigned32
	UNITS		"1"
	MAX-ACCESS	read-write
	STATUS		current
	DESCRIPTION "Tx Queue VLAN ID,
			    0=None
			Oid=1.3.6.1.4.1.31968.3.1.4.1.10.1.9
			"
	::= { txConfigEntry 9 }

txVcmRxChannel OBJECT-TYPE
	SYNTAX		Unsigned32
	UNITS		"1"
	MAX-ACCESS	read-write
	STATUS		current
	DESCRIPTION "Tx Queue Paired Rx Channel
			Oid=1.3.6.1.4.1.31968.3.1.4.1.10.1.10
			"
	::= { txConfigEntry 10 }

txVcmCirMode OBJECT-TYPE
	SYNTAX		INTEGER {
		normal(0),
		periodic(1)
	}
	MAX-ACCESS	read-write
	STATUS		current
	DESCRIPTION "Tx Queue CIR Mode, where:
			    0) 'Normal'
			    1) 'Periodic'
			Oid=1.3.6.1.4.1.31968.3.1.4.1.10.1.11
			"
	::= { txConfigEntry 11 }

txVcmDesiredCir OBJECT-TYPE
	SYNTAX		Unsigned32
	UNITS		"1 bps"
	MAX-ACCESS	read-write
	STATUS		current
	DESCRIPTION "Tx Desired Queue CIR
			Oid=1.3.6.1.4.1.31968.3.1.4.1.10.1.12
			"
	::= { txConfigEntry 12 }

txVcmMir OBJECT-TYPE
	SYNTAX		Unsigned32
	UNITS		"1 bps"
	MAX-ACCESS	read-write
	STATUS		current
	DESCRIPTION "Tx Queue MIR
			Oid=1.3.6.1.4.1.31968.3.1.4.1.10.1.13
			"
	::= { txConfigEntry 13 }

txVcmMinEsn0 OBJECT-TYPE
	SYNTAX		Integer32
	UNITS		"0.01 dB"
	MAX-ACCESS	read-write
	STATUS		current
	DESCRIPTION "Tx Queue Min Es/N0
			Oid=1.3.6.1.4.1.31968.3.1.4.1.10.1.14
			"
	::= { txConfigEntry 14 }

txVcmMaxEsn0 OBJECT-TYPE
	SYNTAX		Integer32
	UNITS		"0.01 dB"
	MAX-ACCESS	read-write
	STATUS		current
	DESCRIPTION "Tx Queue Max Es/N0
			Oid=1.3.6.1.4.1.31968.3.1.4.1.10.1.15
			"
	::= { txConfigEntry 15 }

txVcmFixedModcod OBJECT-TYPE
	SYNTAX		INTEGER {
		qpsk1x4Normal(0),
		qpsk1x4NormalWithPilot(1),
		qpsk13x45Normal(2),
		qpsk13x45NormalWithPilot(3),
		qpsk1x3Normal(4),
		qpsk1x3NormalWithPilot(5),
		qpsk2x5Normal(6),
		qpsk2x5NormalWithPilot(7),
		qpsk9x20Normal(8),
		qpsk9x20NormalWithPilot(9),
		qpsk1x2Normal(10),
		qpsk1x2NormalWithPilot(11),
		qpsk11x20Normal(12),
		qpsk11x20NormalWithPilot(13),
		qpsk3x5Normal(14),
		qpsk3x5NormalWithPilot(15),
		qpsk2x3Normal(16),
		qpsk2x3NormalWithPilot(17),
		qpsk3x4Normal(18),
		qpsk3x4NormalWithPilot(19),
		qpsk4x5Normal(20),
		qpsk4x5NormalWithPilot(21),
		qpsk5x6Normal(22),
		qpsk5x6NormalWithPilot(23),
		qpsk8x9Normal(24),
		qpsk8x9NormalWithPilot(25),
		qpsk9x10Normal(26),
		qpsk9x10NormalWithPilot(27),
		n8apsk5x9LNormal(28),
		n8apsk5x9LNormalWithPilot(29),
		n8apsk26x45LNormal(30),
		n8apsk26x45LNormalWithPilot(31),
		n8psk3x5NormalWithPilot(32),
		n8psk23x36Normal(33),
		n8psk23x36NormalWithPilot(34),
		n8psk2x3NormalWithPilot(35),
		n8psk25x36Normal(36),
		n8psk25x36NormalWithPilot(37),
		n8psk13x18Normal(38),
		n8psk13x18NormalWithPilot(39),
		n8psk3x4Normal(40),
		n8psk3x4NormalWithPilot(41),
		n8psk5x6Normal(42),
		n8psk5x6NormalWithPilot(43),
		n8psk8x9Normal(44),
		n8psk8x9NormalWithPilot(45),
		n8psk9x10Normal(46),
		n8psk9x10NormalWithPilot(47),
		n16apsk1x2LNormal(48),
		n16apsk1x2LNormalWithPilot(49),
		n16apsk8x15LNormal(50),
		n16apsk8x15LNormalWithPilot(51),
		n16apsk5x9LNormal(52),
		n16apsk5x9LNormalWithPilot(53),
		n16apsk26x45Normal(54),
		n16apsk26x45NormalWithPilot(55),
		n16apsk3x5Normal(56),
		n16apsk3x5NormalWithPilot(57),
		n16apsk3x5LNormal(58),
		n16apsk3x5LNormalWithPilot(59),
		n16apsk28x45Normal(60),
		n16apsk28x45NormalWithPilot(61),
		n16apsk23x36Normal(62),
		n16apsk23x36NormalWithPilot(63),
		n16apsk2x3LNormal(64),
		n16apsk2x3LNormalWithPilot(65),
		n16apsk2x3Normal(66),
		n16apsk2x3NormalWithPilot(67),
		n16apsk25x36Normal(68),
		n16apsk25x36NormalWithPilot(69),
		n16apsk13x18Normal(70),
		n16apsk13x18NormalWithPilot(71),
		n16apsk3x4NormalWithPilot(72),
		n16apsk7x9Normal(73),
		n16apsk7x9NormalWithPilot(74),
		n16apsk4x5Normal(75),
		n16apsk4x5NormalWithPilot(76),
		n16apsk5x6Normal(77),
		n16apsk5x6NormalWithPilot(78),
		n16apsk77x90Normal(79),
		n16apsk77x90NormalWithPilot(80),
		n16apsk8x9Normal(81),
		n16apsk8x9NormalWithPilot(82),
		n16apsk9x10Normal(83),
		n16apsk9x10NormalWithPilot(84),
		n32apsk2x3LNormal(85),
		n32apsk2x3LNormalWithPilot(86),
		n32apsk32x45Normal(87),
		n32apsk32x45NormalWithPilot(88),
		n32apsk11x15Normal(89),
		n32apsk11x15NormalWithPilot(90),
		n32apsk3x4Normal(91),
		n32apsk3x4NormalWithPilot(92),
		n32apsk7x9Normal(93),
		n32apsk7x9NormalWithPilot(94),
		n32apsk4x5NormalWithPilot(95),
		n32apsk5x6Normal(96),
		n32apsk5x6NormalWithPilot(97),
		n32apsk8x9Normal(98),
		n32apsk8x9NormalWithPilot(99),
		n32apsk9x10Normal(100),
		n32apsk9x10NormalWithPilot(101),
		n64apsk32x45LNormal(102),
		n64apsk32x45LNormalWithPilot(103),
		n64apsk11x15Normal(104),
		n64apsk11x15NormalWithPilot(105),
		n64apsk7x9Normal(106),
		n64apsk7x9NormalWithPilot(107),
		n64apsk4x5Normal(108),
		n64apsk4x5NormalWithPilot(109),
		n64apsk5x6Normal(110),
		n64apsk5x6NormalWithPilot(111),
		n128apsk3x4Normal(112),
		n128apsk3x4NormalWithPilot(113),
		n128apsk7x9Normal(114),
		n128apsk7x9NormalWithPilot(115),
		n256apsk29x45LNormal(116),
		n256apsk29x45LNormalWithPilot(117),
		n256apsk2x3LNormal(118),
		n256apsk2x3LNormalWithPilot(119),
		n256apsk31x45LNormal(120),
		n256apsk31x45LNormalWithPilot(121),
		n256apsk32x45Normal(122),
		n256apsk32x45NormalWithPilot(123),
		n256apsk11x15LNormal(124),
		n256apsk11x15LNormalWithPilot(125),
		n256apsk3x4Normal(126),
		n256apsk3x4NormalWithPilot(127),
		qpsk1x4Short(128),
		qpsk1x4ShortWithPilot(129),
		qpsk11x45Short(130),
		qpsk11x45ShortWithPilot(131),
		qpsk4x15Short(132),
		qpsk4x15ShortWithPilot(133),
		qpsk14x45Short(134),
		qpsk14x45ShortWithPilot(135),
		qpsk1x3Short(136),
		qpsk1x3ShortWithPilot(137),
		qpsk2x5Short(138),
		qpsk2x5ShortWithPilot(139),
		qpsk1x2Short(140),
		qpsk1x2ShortWithPilot(141),
		qpsk7x15Short(142),
		qpsk7x15ShortWithPilot(143),
		qpsk8x15Short(144),
		qpsk8x15ShortWithPilot(145),
		qpsk3x5Short(146),
		qpsk3x5ShortWithPilot(147),
		qpsk2x3Short(148),
		qpsk2x3ShortWithPilot(149),
		qpsk32x45Short(150),
		qpsk32x45ShortWithPilot(151),
		qpsk3x4Short(152),
		qpsk3x4ShortWithPilot(153),
		qpsk4x5Short(154),
		qpsk4x5ShortWithPilot(155),
		qpsk5x6Short(156),
		qpsk5x6ShortWithPilot(157),
		qpsk8x9Short(158),
		qpsk8x9ShortWithPilot(159),
		n8psk7x15Short(160),
		n8psk7x15ShortWithPilot(161),
		n8psk8x15Short(162),
		n8psk8x15ShortWithPilot(163),
		n8psk26x45Short(164),
		n8psk26x45ShortWithPilot(165),
		n8psk3x5ShortWithPilot(166),
		n8psk2x3ShortWithPilot(167),
		n8psk32x45Short(168),
		n8psk32x45ShortWithPilot(169),
		n8psk3x4Short(170),
		n8psk3x4ShortWithPilot(171),
		n8psk5x6Short(172),
		n8psk5x6ShortWithPilot(173),
		n8psk8x9Short(174),
		n8psk8x9ShortWithPilot(175),
		n16apsk7x15Short(176),
		n16apsk7x15ShortWithPilot(177),
		n16apsk8x15Short(178),
		n16apsk8x15ShortWithPilot(179),
		n16apsk26x45Short(180),
		n16apsk26x45ShortWithPilot(181),
		n16apsk3x5Short(182),
		n16apsk3x5ShortWithPilot(183),
		n16apsk2x3Short(184),
		n16apsk2x3ShortWithPilot(185),
		n16apsk32x45Short(186),
		n16apsk32x45ShortWithPilot(187),
		n16apsk3x4ShortWithPilot(188),
		n16apsk4x5Short(189),
		n16apsk4x5ShortWithPilot(190),
		n16apsk5x6Short(191),
		n16apsk5x6ShortWithPilot(192),
		n16apsk8x9Short(193),
		n16apsk8x9ShortWithPilot(194),
		n32apsk2x3Short(195),
		n32apsk2x3ShortWithPilot(196),
		n32apsk32x45Short(197),
		n32apsk32x45ShortWithPilot(198),
		n32apsk3x4Short(199),
		n32apsk3x4ShortWithPilot(200),
		n32apsk4x5ShortWithPilot(201),
		n32apsk5x6Short(202),
		n32apsk5x6ShortWithPilot(203),
		n32apsk8x9Short(204),
		n32apsk8x9ShortWithPilot(205)
	}
	MAX-ACCESS	read-write
	STATUS		current
	DESCRIPTION "Tx Queue Fixed ModCod, where:
			    0) 'QPSK 1/4 Normal'
			    1) 'QPSK 1/4 Normal with Pilot'
			    2) 'QPSK 13/45 Normal'
			    3) 'QPSK 13/45 Normal with Pilot'
			    4) 'QPSK 1/3 Normal'
			    5) 'QPSK 1/3 Normal with Pilot'
			    6) 'QPSK 2/5 Normal'
			    7) 'QPSK 2/5 Normal with Pilot'
			    8) 'QPSK 9/20 Normal'
			    9) 'QPSK 9/20 Normal with Pilot'
			    10) 'QPSK 1/2 Normal'
			    11) 'QPSK 1/2 Normal with Pilot'
			    12) 'QPSK 11/20 Normal'
			    13) 'QPSK 11/20 Normal with Pilot'
			    14) 'QPSK 3/5 Normal'
			    15) 'QPSK 3/5 Normal with Pilot'
			    16) 'QPSK 2/3 Normal'
			    17) 'QPSK 2/3 Normal with Pilot'
			    18) 'QPSK 3/4 Normal'
			    19) 'QPSK 3/4 Normal with Pilot'
			    20) 'QPSK 4/5 Normal'
			    21) 'QPSK 4/5 Normal with Pilot'
			    22) 'QPSK 5/6 Normal'
			    23) 'QPSK 5/6 Normal with Pilot'
			    24) 'QPSK 8/9 Normal'
			    25) 'QPSK 8/9 Normal with Pilot'
			    26) 'QPSK 9/10 Normal'
			    27) 'QPSK 9/10 Normal with Pilot'
			    28) '8APSK 5/9-L Normal'
			    29) '8APSK 5/9-L Normal with Pilot'
			    30) '8APSK 26/45-L Normal'
			    31) '8APSK 26/45-L Normal with Pilot'
			    32) '8PSK 3/5 Normal with Pilot'
			    33) '8PSK 23/36 Normal'
			    34) '8PSK 23/36 Normal with Pilot'
			    35) '8PSK 2/3 Normal with Pilot'
			    36) '8PSK 25/36 Normal'
			    37) '8PSK 25/36 Normal with Pilot'
			    38) '8PSK 13/18 Normal'
			    39) '8PSK 13/18 Normal with Pilot'
			    40) '8PSK 3/4 Normal'
			    41) '8PSK 3/4 Normal with Pilot'
			    42) '8PSK 5/6 Normal'
			    43) '8PSK 5/6 Normal with Pilot'
			    44) '8PSK 8/9 Normal'
			    45) '8PSK 8/9 Normal with Pilot'
			    46) '8PSK 9/10 Normal'
			    47) '8PSK 9/10 Normal with Pilot'
			    48) '16APSK 1/2-L Normal'
			    49) '16APSK 1/2-L Normal with Pilot'
			    50) '16APSK 8/15-L Normal'
			    51) '16APSK 8/15-L Normal with Pilot'
			    52) '16APSK 5/9-L Normal'
			    53) '16APSK 5/9-L Normal with Pilot'
			    54) '16APSK 26/45 Normal'
			    55) '16APSK 26/45 Normal with Pilot'
			    56) '16APSK 3/5 Normal'
			    57) '16APSK 3/5 Normal with Pilot'
			    58) '16APSK 3/5-L Normal'
			    59) '16APSK 3/5-L Normal with Pilot'
			    60) '16APSK 28/45 Normal'
			    61) '16APSK 28/45 Normal with Pilot'
			    62) '16APSK 23/36 Normal'
			    63) '16APSK 23/36 Normal with Pilot'
			    64) '16APSK 2/3-L Normal'
			    65) '16APSK 2/3-L Normal with Pilot'
			    66) '16APSK 2/3 Normal'
			    67) '16APSK 2/3 Normal with Pilot'
			    68) '16APSK 25/36 Normal'
			    69) '16APSK 25/36 Normal with Pilot'
			    70) '16APSK 13/18 Normal'
			    71) '16APSK 13/18 Normal with Pilot'
			    72) '16APSK 3/4 Normal with Pilot'
			    73) '16APSK 7/9 Normal'
			    74) '16APSK 7/9 Normal with Pilot'
			    75) '16APSK 4/5 Normal'
			    76) '16APSK 4/5 Normal with Pilot'
			    77) '16APSK 5/6 Normal'
			    78) '16APSK 5/6 Normal with Pilot'
			    79) '16APSK 77/90 Normal'
			    80) '16APSK 77/90 Normal with Pilot'
			    81) '16APSK 8/9 Normal'
			    82) '16APSK 8/9 Normal with Pilot'
			    83) '16APSK 9/10 Normal'
			    84) '16APSK 9/10 Normal with Pilot'
			    85) '32APSK 2/3-L Normal'
			    86) '32APSK 2/3-L Normal with Pilot'
			    87) '32APSK 32/45 Normal'
			    88) '32APSK 32/45 Normal with Pilot'
			    89) '32APSK 11/15 Normal'
			    90) '32APSK 11/15 Normal with Pilot'
			    91) '32APSK 3/4 Normal'
			    92) '32APSK 3/4 Normal with Pilot'
			    93) '32APSK 7/9 Normal'
			    94) '32APSK 7/9 Normal with Pilot'
			    95) '32APSK 4/5 Normal with Pilot'
			    96) '32APSK 5/6 Normal'
			    97) '32APSK 5/6 Normal with Pilot'
			    98) '32APSK 8/9 Normal'
			    99) '32APSK 8/9 Normal with Pilot'
			    100) '32APSK 9/10 Normal'
			    101) '32APSK 9/10 Normal with Pilot'
			    102) '64APSK 32/45-L Normal'
			    103) '64APSK 32/45-L Normal with Pilot'
			    104) '64APSK 11/15 Normal'
			    105) '64APSK 11/15 Normal with Pilot'
			    106) '64APSK 7/9 Normal'
			    107) '64APSK 7/9 Normal with Pilot'
			    108) '64APSK 4/5 Normal'
			    109) '64APSK 4/5 Normal with Pilot'
			    110) '64APSK 5/6 Normal'
			    111) '64APSK 5/6 Normal with Pilot'
			    112) '128APSK 3/4 Normal'
			    113) '128APSK 3/4 Normal with Pilot'
			    114) '128APSK 7/9 Normal'
			    115) '128APSK 7/9 Normal with Pilot'
			    116) '256APSK 29/45-L Normal'
			    117) '256APSK 29/45-L Normal with Pilot'
			    118) '256APSK 2/3-L Normal'
			    119) '256APSK 2/3-L Normal with Pilot'
			    120) '256APSK 31/45-L Normal'
			    121) '256APSK 31/45-L Normal with Pilot'
			    122) '256APSK 32/45 Normal'
			    123) '256APSK 32/45 Normal with Pilot'
			    124) '256APSK 11/15-L Normal'
			    125) '256APSK 11/15-L Normal with Pilot'
			    126) '256APSK 3/4 Normal'
			    127) '256APSK 3/4 Normal with Pilot'
			    128) 'QPSK 1/4 Short'
			    129) 'QPSK 1/4 Short with Pilot'
			    130) 'QPSK 11/45 Short'
			    131) 'QPSK 11/45 Short with Pilot'
			    132) 'QPSK 4/15 Short'
			    133) 'QPSK 4/15 Short with Pilot'
			    134) 'QPSK 14/45 Short'
			    135) 'QPSK 14/45 Short with Pilot'
			    136) 'QPSK 1/3 Short'
			    137) 'QPSK 1/3 Short with Pilot'
			    138) 'QPSK 2/5 Short'
			    139) 'QPSK 2/5 Short with Pilot'
			    140) 'QPSK 1/2 Short'
			    141) 'QPSK 1/2 Short with Pilot'
			    142) 'QPSK 7/15 Short'
			    143) 'QPSK 7/15 Short with Pilot'
			    144) 'QPSK 8/15 Short'
			    145) 'QPSK 8/15 Short with Pilot'
			    146) 'QPSK 3/5 Short'
			    147) 'QPSK 3/5 Short with Pilot'
			    148) 'QPSK 2/3 Short'
			    149) 'QPSK 2/3 Short with Pilot'
			    150) 'QPSK 32/45 Short'
			    151) 'QPSK 32/45 Short with Pilot'
			    152) 'QPSK 3/4 Short'
			    153) 'QPSK 3/4 Short with Pilot'
			    154) 'QPSK 4/5 Short'
			    155) 'QPSK 4/5 Short with Pilot'
			    156) 'QPSK 5/6 Short'
			    157) 'QPSK 5/6 Short with Pilot'
			    158) 'QPSK 8/9 Short'
			    159) 'QPSK 8/9 Short with Pilot'
			    160) '8PSK 7/15 Short'
			    161) '8PSK 7/15 Short with Pilot'
			    162) '8PSK 8/15 Short'
			    163) '8PSK 8/15 Short with Pilot'
			    164) '8PSK 26/45 Short'
			    165) '8PSK 26/45 Short with Pilot'
			    166) '8PSK 3/5 Short with Pilot'
			    167) '8PSK 2/3 Short with Pilot'
			    168) '8PSK 32/45 Short'
			    169) '8PSK 32/45 Short with Pilot'
			    170) '8PSK 3/4 Short'
			    171) '8PSK 3/4 Short with Pilot'
			    172) '8PSK 5/6 Short'
			    173) '8PSK 5/6 Short with Pilot'
			    174) '8PSK 8/9 Short'
			    175) '8PSK 8/9 Short with Pilot'
			    176) '16APSK 7/15 Short'
			    177) '16APSK 7/15 Short with Pilot'
			    178) '16APSK 8/15 Short'
			    179) '16APSK 8/15 Short with Pilot'
			    180) '16APSK 26/45 Short'
			    181) '16APSK 26/45 Short with Pilot'
			    182) '16APSK 3/5 Short'
			    183) '16APSK 3/5 Short with Pilot'
			    184) '16APSK 2/3 Short'
			    185) '16APSK 2/3 Short with Pilot'
			    186) '16APSK 32/45 Short'
			    187) '16APSK 32/45 Short with Pilot'
			    188) '16APSK 3/4 Short with Pilot'
			    189) '16APSK 4/5 Short'
			    190) '16APSK 4/5 Short with Pilot'
			    191) '16APSK 5/6 Short'
			    192) '16APSK 5/6 Short with Pilot'
			    193) '16APSK 8/9 Short'
			    194) '16APSK 8/9 Short with Pilot'
			    195) '32APSK 2/3 Short'
			    196) '32APSK 2/3 Short with Pilot'
			    197) '32APSK 32/45 Short'
			    198) '32APSK 32/45 Short with Pilot'
			    199) '32APSK 3/4 Short'
			    200) '32APSK 3/4 Short with Pilot'
			    201) '32APSK 4/5 Short with Pilot'
			    202) '32APSK 5/6 Short'
			    203) '32APSK 5/6 Short with Pilot'
			    204) '32APSK 8/9 Short'
			    205) '32APSK 8/9 Short with Pilot'
			Oid=1.3.6.1.4.1.31968.3.1.4.1.10.1.16
			"
	::= { txConfigEntry 16 }

txVcmMinModcodAlarm OBJECT-TYPE
	SYNTAX		INTEGER {
		off(0),
		report(1),
		alarm(3),
		alarmAndRelayOutput(5)
	}
	MAX-ACCESS	read-write
	STATUS		current
	DESCRIPTION "Tx Queue Minimum ModCod Alarm, where:
			    0) 'Off'
			    1) 'Report'
			    3) 'Alarm'
			    5) 'Alarm & Relay Output'
			Oid=1.3.6.1.4.1.31968.3.1.4.1.10.1.17
			"
	::= { txConfigEntry 17 }

txVcmLowEsn0Alarm OBJECT-TYPE
	SYNTAX		INTEGER {
		off(0),
		report(1),
		alarm(3),
		alarmAndRelayOutput(5)
	}
	MAX-ACCESS	read-write
	STATUS		current
	DESCRIPTION "Tx Queue Low Es/N0 Alarm, where:
			    0) 'Off'
			    1) 'Report'
			    3) 'Alarm'
			    5) 'Alarm & Relay Output'
			Oid=1.3.6.1.4.1.31968.3.1.4.1.10.1.18
			"
	::= { txConfigEntry 18 }

txVcmLowEsn0Limit OBJECT-TYPE
	SYNTAX		Integer32
	UNITS		"0.01 dB"
	MAX-ACCESS	read-write
	STATUS		current
	DESCRIPTION "Tx Queue Low Es/N0 Limit
			Oid=1.3.6.1.4.1.31968.3.1.4.1.10.1.19
			"
	::= { txConfigEntry 19 }

txVcmMccChannelAlarm OBJECT-TYPE
	SYNTAX		INTEGER {
		off(0),
		report(1),
		alarm(3),
		alarmAndRelayOutput(5)
	}
	MAX-ACCESS	read-write
	STATUS		current
	DESCRIPTION "Tx Queue MCC Remote Channel Alarm, where:
			    0) 'Off'
			    1) 'Report'
			    3) 'Alarm'
			    5) 'Alarm & Relay Output'
			Oid=1.3.6.1.4.1.31968.3.1.4.1.10.1.20
			"
	::= { txConfigEntry 20 }

txVcmDataAlarm OBJECT-TYPE
	SYNTAX		INTEGER {
		off(0),
		report(1),
		reportMuteTxOutput(2),
		alarm(3),
		alarmAndMuteTxOutput(4),
		alarmAndRelayOutput(5),
		alarmAndRelayOutputAndMuteTxOutput(6)
	}
	MAX-ACCESS	read-write
	STATUS		current
	DESCRIPTION "Tx Queue Data Inactive Alarm, where:
			    0) 'Off'
			    1) 'Report'
			    2) 'Report, Mute Tx Output'
			    3) 'Alarm'
			    4) 'Alarm & Mute Tx Output'
			    5) 'Alarm & Relay Output'
			    6) 'Alarm & Relay Output & Mute Tx Output'
			Oid=1.3.6.1.4.1.31968.3.1.4.1.10.1.21
			"
	::= { txConfigEntry 21 }

txVcmDataInactive OBJECT-TYPE
	SYNTAX		Unsigned32
	UNITS		"s"
	MAX-ACCESS	read-write
	STATUS		current
	DESCRIPTION "Tx Queue Data Inactive Time
			Oid=1.3.6.1.4.1.31968.3.1.4.1.10.1.22
			"
	::= { txConfigEntry 22 }

txVcmMccChannelEvent OBJECT-TYPE
	SYNTAX		INTEGER {
		doNotLog(0),
		log(1),
		logAndSendAlert(2),
		logAndSendAlertNowNoDebounce(3)
	}
	MAX-ACCESS	read-write
	STATUS		current
	DESCRIPTION "Tx Queue MCC Remote Channel Alarm Event, where:
			    0) 'Do Not Log'
			    1) 'Log'
			    2) 'Log & Send Alert'
			    3) 'Log & Send Alert Now (No Debounce)'
			Oid=1.3.6.1.4.1.31968.3.1.4.1.10.1.23
			"
	::= { txConfigEntry 23 }

txVcmMinModcodEvent OBJECT-TYPE
	SYNTAX		INTEGER {
		doNotLog(0),
		log(1),
		logAndSendAlert(2),
		logAndSendAlertNowNoDebounce(3)
	}
	MAX-ACCESS	read-write
	STATUS		current
	DESCRIPTION "Tx Queue Minimum ModCod Alarm Event, where:
			    0) 'Do Not Log'
			    1) 'Log'
			    2) 'Log & Send Alert'
			    3) 'Log & Send Alert Now (No Debounce)'
			Oid=1.3.6.1.4.1.31968.3.1.4.1.10.1.24
			"
	::= { txConfigEntry 24 }

txVcmLowEsn0Event OBJECT-TYPE
	SYNTAX		INTEGER {
		doNotLog(0),
		log(1),
		logAndSendAlert(2),
		logAndSendAlertNowNoDebounce(3)
	}
	MAX-ACCESS	read-write
	STATUS		current
	DESCRIPTION "Tx Queue Low Es/N0 Alarm Event, where:
			    0) 'Do Not Log'
			    1) 'Log'
			    2) 'Log & Send Alert'
			    3) 'Log & Send Alert Now (No Debounce)'
			Oid=1.3.6.1.4.1.31968.3.1.4.1.10.1.25
			"
	::= { txConfigEntry 25 }

txVcmDataEvent OBJECT-TYPE
	SYNTAX		INTEGER {
		doNotLog(0),
		log(1),
		logAndSendAlert(2),
		logAndSendAlertNowNoDebounce(3)
	}
	MAX-ACCESS	read-write
	STATUS		current
	DESCRIPTION "Tx Queue Data Inactivity Alarm Event, where:
			    0) 'Do Not Log'
			    1) 'Log'
			    2) 'Log & Send Alert'
			    3) 'Log & Send Alert Now (No Debounce)'
			Oid=1.3.6.1.4.1.31968.3.1.4.1.10.1.26
			"
	::= { txConfigEntry 26 }

txVcmId OBJECT-TYPE
	SYNTAX		DisplayString(SIZE(0..28))
	MAX-ACCESS	read-write
	STATUS		current
	DESCRIPTION "Tx Queue Remote ID
			Oid=1.3.6.1.4.1.31968.3.1.4.1.10.1.27
			"
	::= { txConfigEntry 27 }

totalEvents OBJECT-TYPE
	SYNTAX		Unsigned32
	UNITS		"1"
	MAX-ACCESS	read-only
	STATUS		current
	DESCRIPTION "Total Events
			Oid=1.3.6.1.4.1.31968.3.1.4.1.11.1
			"
	::= { eventLogItems 1 }

eventLogTable OBJECT-TYPE
	SYNTAX		SEQUENCE OF EventLogEntry
	MAX-ACCESS	not-accessible
	STATUS		current
	DESCRIPTION "Event Log Entry Table
			Oid=1.3.6.1.4.1.31968.3.1.4.1.12
			"
	::= { m7xcModemObjs 12 }

eventLogEntry OBJECT-TYPE
	SYNTAX		EventLogEntry
	MAX-ACCESS	not-accessible
	STATUS		current
	DESCRIPTION "Event Log Entry Entry
			Oid=1.3.6.1.4.1.31968.3.1.4.1.12.1
			"
	INDEX {
		eventLogIndex
	}
	::= { eventLogTable 1 }

EventLogEntry ::=
	SEQUENCE {
		eventLogIndex           Unsigned32,
		eventLog                DisplayString
	}

eventLogIndex OBJECT-TYPE
	SYNTAX		Unsigned32(1..16)
	MAX-ACCESS	not-accessible
	STATUS		current
	DESCRIPTION "Event Log Entry Index
			Oid=1.3.6.1.4.1.31968.3.1.4.1.12.1.1
			"
	::= { eventLogEntry 1 }

eventLog OBJECT-TYPE
	SYNTAX		DisplayString(SIZE(0..255))
	MAX-ACCESS	read-only
	STATUS		current
	DESCRIPTION "Events
			Oid=1.3.6.1.4.1.31968.3.1.4.1.12.1.2
			"
	::= { eventLogEntry 2 }

unitInfoGroups OBJECT IDENTIFIER ::= { m7xcModemConformance 2 }

unitInfoGroup OBJECT-GROUP
	OBJECTS {
		unitStatus,
		unitBinaryStatus,
		powerVoltage,
		model,
		sn,
		firmware,
		build,
		trialTime,
		mgmtPortStatus,
		mgmtMacAddress,
		refStatus,
		monOutVoltage,
		monInVoltage,
		dataPortStatus,
		cpuTemp,
		txTemp,
		fpga1Temp,
		rxTemp,
		fpga2Temp,
		fpga3Temp,
		unitCalStatus,
		unitRefCal,
		overTempShutdowns,
		tleDatabase,
		satName,
		satCatalog,
		satClassification,
		satLaunchYear,
		satLaunchNumber,
		satLaunchPiece,
		satEphemeris,
		satEpochYear,
		satEpochDay,
		satRevolution,
		tleSetNumber,
		satMeanMotion,
		satFirstMotion,
		satSecondMotion,
		satDrag,
		satInclination,
		satAscension,
		satEccentricity,
		satPerigee,
		satAnomaly,
		snmpInformTotalRetryTime,
		batteryVoltage,
		fipsStatus,
		snmpAlert1InformStatus,
		snmpAlert2InformStatus,
		snmpAlert3InformStatus,
		snmpAlert4InformStatus,
		snmpAuthEngineId,
		snmpAuthEngineBoots,
		unitBoots,
		acuStatus,
		acuFunctional,
		acuTxAllowed,
		acuTxDisabled,
		acuId,
		acuGpsLocation,
		acuGpsTime,
		acuGpsLatitude,
		acuGpsLongitude,
		acuGpsAltitude,
		acuGpsHeading,
		acuGpsSpeed,
		acuGpsPitch,
		acuGpsRoll,
		acuGpsYaw,
		acuGpsSkew,
		acuSearchCount,
		acuLockStatInterval,
		acuConRate,
		acuAzPos,
		acuAzNeg,
		acuElPos,
		acuElNeg,
		redunStatus,
		fipsAssembly,
		fipsFpgaId,
		fipsFpgaBuild,
		fipsSn,
		fipsSelfTests,
		fipsTemp,
		fipsLastLog,
		ntpServerStatus,
		stationId,
		dateTime,
		powerMin,
		powerAlarm,
		trial7daysAlarm,
		trial24hoursAlarm,
		unitTestAlarm,
		hardwareAlarm,
		reboot,
		featureActivation,
		trialActivation,
		admin,
		httpServerProtocol,
		httpReadName,
		httpReadPassword,
		httpFullName,
		httpFullPassword,
		httpActivity,
		snmpAgentMode,
		snmpAgentProtocol,
		snmpAgentPort,
		snmpReadName,
		snmpFullName,
		snmpAlert1Name,
		snmpAlert2Name,
		snmpAlert3Name,
		snmpAlert4Name,
		snmpAlert1Mode,
		snmpAlert2Mode,
		snmpAlert3Mode,
		snmpAlert4Mode,
		snmpAlert1Address,
		snmpAlert2Address,
		snmpAlert3Address,
		snmpAlert4Address,
		snmpAlert1Port,
		snmpAlert2Port,
		snmpAlert3Port,
		snmpAlert4Port,
		snmpInformRetries,
		snmpInformTimeout,
		snmpActivity,
		mgmtDhcp,
		mgmtAddress,
		mgmtMask,
		mgmtGateway,
		mgmtDns1,
		mgmtDns2,
		mgmtUdpServerMode,
		mgmtUdpServerPort,
		mgmtUdpRemotePath,
		mgmtUdpExternalUnit,
		mgmtUdpActivity,
		rs232Mode,
		rs232Protocol,
		rs232Address,
		rs232Rate,
		rs232Format,
		rs232Activity,
		refSource,
		refFrequency,
		refFineTune,
		eventDebounce,
		refAlarm,
		refOcxoOven,
		monOutMode,
		monOutScale,
		monOutSlope,
		monAlarm,
		monInThreshold,
		monInSense,
		redundancy,
		eventPendingAlarm,
		mgmtLinkAlarm,
		dataLinkAlarm,
		eventDisplay,
		eventFilter,
		powerEvent,
		trialEvent,
		unitTestEvent,
		refEvent,
		monEvent,
		redundancyEvent,
		mgmtLinkEvent,
		dataLinkEvent,
		startupEvent,
		httpAccessEvent,
		snmpAccessEvent,
		configStoreEvent,
		dataPortOffline,
		configChangeEvent,
		unitCalibration,
		unitCalTask,
		storeRecallLocation,
		storeRecallDescription,
		storeRecallOperation,
		autoRestore,
		autoRestoreAfter,
		autoRestoreLocation,
		configStartup,
		satId,
		beamId,
		mgmtVlanId,
		mgmtMccBridge,
		mgmtFilter,
		mgmtFilterRangeStart,
		mgmtFilterRangeEnd,
		mgmtIngressVlanFilter,
		mgmtEgressVlanFilter,
		mgmtVlanFilterTagStart,
		mgmtVlanFilterTagEnd,
		dataIngressVlanFilter,
		dataEgressVlanFilter,
		dataVlanFilterId,
		dataVlanFilterTagStart,
		dataVlanFilterTagEnd,
		dataEchoFilter,
		eventClear,
		configRestoreEvent,
		systemEvent,
		timeEvent,
		autoRestoreWhen,
		satFind,
		satSearchOperation,
		satTle,
		batteryAlarm,
		snmpReadAuthEncryption,
		snmpReadPrivEncryption,
		snmpFullAuthEncryption,
		snmpFullPrivEncryption,
		snmpReadUsername,
		snmpReadAuthPassword,
		snmpReadPrivPassword,
		snmpFullUsername,
		snmpFullAuthPassword,
		snmpFullPrivPassword,
		snmpAlertProtocol,
		snmpAlertAuthEncryption,
		snmpAlertPrivEncryption,
		snmpAlertUsername,
		snmpAlertAuthPassword,
		snmpAlertPrivPassword,
		batteryEvent,
		dataPortLink,
		acuOperation,
		acuIpProtocol,
		acuAddr,
		acuPort,
		acuVersion,
		acuAliveInterval,
		acuLocationInterval,
		acuTxPolarization,
		acuRxPolarization,
		acuMinSkew,
		acuMaxSkew,
		acuTxCableLoss,
		acuRegulationType,
		acuRegReportingInterval,
		acuSatLongitude,
		acuSatLatitudeVariance,
		acuPolarizationSkew,
		acuSendCommand,
		acuHuntFreq,
		acuHuntBandwidth,
		acuRxChannel,
		acuAlarm,
		acuEvent,
		redundancyRole,
		redundancyPreference,
		redundancyComs,
		redundancyPartnerIp,
		redundancySwitchDelay,
		redundancyLossAction,
		redundancyConfigTransfer,
		redundancyPort,
		redundancyAlarm,
		redundancyRevDelay,
		fipsSelfTest,
		fipsAuthenication,
		fipsAuthenicationIdentifier,
		sshServerMode,
		sshServerPort,
		sshReadName,
		sshReadPassword,
		sshFullName,
		sshFullPassword,
		sshActivity,
		mgmtPortLink,
		dataPortExternalLoop,
		dataPortInternalLoop,
		ntpServer1,
		ntpServer2,
		rxSumStatus,
		rxBinary0Status,
		rxBinary1Status,
		rxEchoLevel,
		rxEchoOffset,
		rxOffsetImbalance,
		rxEchoDelay,
		rxFeatureBitRateLimit,
		rxFeatureSymbolRateLimit,
		rxFeatureModulationLimit,
		rxFeatureChannelLimit,
		rxFeatureWaveforms,
		rxLnbVoltage,
		rxLnbCurrent,
		rxTotalSymbolRate,
		rxEchoDrops,
		rxTotalBitRate,
		rxAnalyzerData,
		rxAnalyzerTick,
		rxCalStatus,
		rxLevelBalCal,
		rxPhaseBalCal,
		rxEqBalCal,
		rxLevelCal,
		rxDmdMemTest,
		rxFecMemTest,
		rxFeatureTransec,
		rxTrialWaveforms,
		rxTrialChannelLimit,
		rxTrialModulationLimit,
		rxTrialTransec,
		rxTrialBitRateLimit,
		rxTrialSymbolRateLimit,
		rxDsssTotalChipRate,
		rxHdrRotorOutage,
		rxStatus,
		rxDvbModcod,
		rxLdpcModcod,
		rxEsn0,
		rxMargin,
		rxLevel,
		rxLevelImbalance,
		rxOffset,
		rxOccupied,
		rxSpectrum,
		rxFrameCount,
		rxFrameErrors,
		rxFrameErrorRate,
		rxRate,
		rxAverageRate,
		rxPps,
		rxAveragePps,
		rxDataPackets,
		rxDataBytes,
		rxIdlePackets,
		rxIdleBytes,
		rxMccPackets,
		rxMccBytes,
		rxAcmPackets,
		rxAcmBytes,
		rxTotalPackets,
		rxTotalBytes,
		rxErredPackets,
		rxTotalPer,
		rxTotalSeconds,
		rxTotalAverage,
		rxTotalRate,
		rxBroadcastRate,
		rxAverageBroadcastRate,
		rxBroadcastPps,
		rxAverageBroadcastPps,
		rxBroadcastPackets,
		rxBroadcastBytes,
		rxTransecStatus,
		rxMccRate,
		rxMccAverage,
		rxAcmRate,
		rxAcmAverage,
		rxTransecKeyIndex,
		rxSnr,
		rxDsssSymbolRate,
		rxDsssModcod,
		rxAcqSweeps,
		rxHdrModcod,
		rxFramePeriod,
		rxWaveform,
		rxTotalChannels,
		rxSmart,
		rxMinDelay,
		rxMaxDelay,
		rxHoldDelay,
		rxEchoLevelLimit,
		rxEchoLevelAlarm,
		rxEchoOffsetLimit,
		rxEchoOffsetAlarm,
		rxRemoteTxEsn0Mode,
		rxLnbLo,
		rxLnbSide,
		rxLnbRef,
		rxLnbPower,
		rxLnbMin,
		rxLnbMax,
		rxLnbAlarm,
		rxLnbCenterFrequency,
		rxCenterFrequency,
		rxGseDataProtocol,
		rxHdlcDataProtocol,
		rxDataIdle,
		rxDataMcc,
		rxLocalIpAddress,
		rxDataHoeSmac,
		rxDataHoeDmac,
		rxMccMode,
		rxMccProtocol,
		rxMccAddress,
		rxActivity,
		rxEchoLevelEvent,
		rxEchoOffsetEvent,
		rxLnbEvent,
		rxRfBandwidth,
		rxAnalyzerLnbCenterFrequency,
		rxAnalyzerCenterFrequency,
		rxAnalyzerSpanFrequency,
		rxAnalyzerDisplay,
		rxAnalyzerLevel,
		rxAnalyzerOffset,
		rxAnalyzerScale,
		rxCalTask,
		rxDataPortLinkRateAlarm,
		rxDataPortLinkRateEvent,
		rxHdrFixedModcod,
		rxHdrRotorThreshold,
		rxHdrRotorLead,
		rxHdrRotorLag,
		rxHdrSymbolRate,
		rxRemoteMacAddress,
		rxAcmTxHubMsgAlarm,
		rxAcmTxHubMsgEvent,
		rxLockAlarm,
		rxEsn0Margin,
		rxEsn0Alarm,
		rxLevelLimit,
		rxLevelAlarm,
		rxAcmLowEsn0Alarm,
		rxAcmLowEsn0Limit,
		rxFrameStatsReset,
		rxTrafficStatsReset,
		rxLnbFrequency,
		rxFrequency,
		rxRollOff,
		rxRemotePath,
		rxRemoteMccAddress,
		rxSymbolRate,
		rxDvbDescrambler,
		rxLdpcBlock,
		rxLdpcDescrambler,
		rxFromTxQueue,
		rxTransecOperation,
		rxDataInactive,
		rxDataAlarm,
		rxLockEvent,
		rxEsn0Event,
		rxLevelEvent,
		rxAcmEvent,
		rxAcmLowEsn0Event,
		rxDataEvent,
		rxChannel,
		rxTransecKeySize,
		rxTransecKey,
		rxTransecKeyHash,
		rxTransecAlarm,
		rxTransecEvent,
		rxMuteTxOutputDelay,
		rxModcodEvent,
		rxDsssChipRate,
		rxDsssSpreadFactor,
		rxDsssCodeLength,
		rxDsssCode,
		rxAcrLowSnrLimit,
		rxMinAcquisitionRange,
		rxRemoteChannelId,
		txStatus,
		txBinaryStatus,
		txDvbModcod,
		txLdpcModcod,
		txRemoteEsn0,
		txFeatureBitRateLimit,
		txFeatureSymbolRateLimit,
		txFeatureSmartCarrierBitRateLimit,
		txFeatureSmartCarrierSymbolRateLimit,
		txFeatureModulationLimit,
		txFeatureChannelLimit,
		txFeatureWaveforms,
		txFeatureTransec,
		txTotalSymbolRate,
		txQueue0DataRate,
		txQueue0AverageRate,
		txQueue0Sent,
		txQueue0Dropped,
		txQueue1DataRate,
		txQueue1AverageRate,
		txQueue1Sent,
		txQueue1Dropped,
		txQueue2DataRate,
		txQueue2AverageRate,
		txQueue2Sent,
		txQueue2Dropped,
		txQueue3DataRate,
		txQueue3AverageRate,
		txQueue3Sent,
		txQueue3Dropped,
		txQueue4DataRate,
		txQueue4AverageRate,
		txQueue4Sent,
		txQueue4Dropped,
		txQueue5DataRate,
		txQueue5AverageRate,
		txQueue5Sent,
		txQueue5Dropped,
		txQueue6DataRate,
		txQueue6AverageRate,
		txQueue6Dropped,
		txQueue7DataRate,
		txQueue7AverageRate,
		txQueue7Sent,
		txQueue7Dropped,
		txEchoDrops,
		txRate,
		txAverageRate,
		txPps,
		txAveragePps,
		txDataPackets,
		txDataBytes,
		txIdlePackets,
		txIdleBytes,
		txMccPackets,
		txMccBytes,
		txAcmPackets,
		txAcmBytes,
		txTotalPackets,
		txTotalBytes,
		txDroppedPackets,
		txTotalPdr,
		txTotalSeconds,
		txTotalAverage,
		txTotalRate,
		txQueue6Sent,
		txTotalBitRate,
		txQueue0Full,
		txQueue1Full,
		txQueue2Full,
		txQueue3Full,
		txQueue4Full,
		txQueue5Full,
		txQueue6Full,
		txQueue7Full,
		txTotalOutputLevel,
		txTransecStatus,
		txTransecKeyIndex,
		txMccRate,
		txMccAverage,
		txAcmRate,
		txAcmAverage,
		txCalStatus,
		txDcOffsetCal,
		txLevelBalCal,
		txPhaseBalCal,
		txDelayBalCal,
		txLevelCal,
		txTiltCal,
		txMemTest,
		txRemoteMargin,
		txTrialWaveforms,
		txTrialChannelLimit,
		txTrialModulationLimit,
		txTrialTransec,
		txTrialBitRateLimit,
		txTrialSymbolRateLimit,
		txTrialSmartCarrierBitRateLimit,
		txTrialSmartCarrierSymbolRateLimit,
		txRemoteSnr,
		txDsssSymbolRate,
		txDsssModcod,
		txVcmAvailableCir,
		txVcmTotalCir,
		txVcmDrainMinModcod,
		txVcmCirMinModcod,
		txVcmBinaryStatus,
		txHdrModcod,
		txFramePeriod,
		txTableStatus,
		txOccupied,
		txVcmStatus,
		txVcmModcod,
		txVcmMargin,
		txVcmEsn0,
		txVcmQueueAverage,
		txVcmQueueRate,
		txVcmQueuePackets,
		txVcmQueueBytes,
		txVcmQueueDropped,
		txVcmQueueFull,
		txWaveform,
		txTotalChannels,
		txBucLo,
		txBucSide,
		txBucRef,
		txBucCenterFrequency,
		txCenterFrequency,
		txTotalMinSymbolRate,
		txTotalMaxSymbolRate,
		txPsdLevel,
		txLevel,
		txMute,
		txRollOff,
		txSpectrum,
		txTilt,
		txAupc,
		txAupcEsn0,
		txAupcMin,
		txAupcMax,
		txAupcLimitAlarm,
		txTrafficStatsReset,
		txDvbService,
		txDvbFrame,
		txDvbPilot,
		txDvbFixedModcod,
		txDvbScrambler,
		txLdpcService,
		txLdpcBlock,
		txLdpcFixedModcod,
		txLdpcScrambler,
		txAcmMinEsn0,
		txAcmMaxEsn0,
		txAcmLowEsn0Alarm,
		txAcmLowEsn0Limit,
		txMccChannelAlarm,
		txAcm2aryHysteresis,
		txAcm4aryHysteresis,
		txAcm8aryHysteresis,
		txAcm16aryHysteresis,
		txAcm32aryHysteresis,
		txAcm64aryHysteresis,
		txAcm128aryHysteresis,
		txAcm256aryHysteresis,
		txAcmMargin,
		txTransecOperation,
		txTransecKeySize,
		txTransecKeyRoll,
		txTransecKey,
		txTransecKeyHash,
		txTransecAlarm,
		txTransecEvent,
		txCalPowerMeterIp,
		txCalPowerMeterPort,
		txAupcAlarm,
		txGseDataProtocol,
		txHdlcDataProtocol,
		txDataIdle,
		txDataMcc,
		txDataHoeSmac,
		txDataHoeDmac,
		txQosMode,
		txQosLive,
		txQos1st,
		txQos2nd,
		txQos3rd,
		txQosDefault,
		txQueue7Weight,
		txQueue7Live,
		txQueue6Weight,
		txQueue6Live,
		txQueue5Weight,
		txQueue5Live,
		txQueue4Weight,
		txQueue4Live,
		txQueue3Weight,
		txQueue3Live,
		txQueue2Weight,
		txQueue2Live,
		txQueue1Weight,
		txQueue1Live,
		txQueue0Weight,
		txQueue0Live,
		txMccProtocol,
		txDvbMccRate,
		txLdpcMccRate,
		txMccAddress,
		txAcmModcodEvent,
		txDataInactive,
		txDataAlarm,
		txCarrierEvent,
		txAupcEvent,
		txMccChannelEvent,
		txAcmLowEsn0Event,
		txDataEvent,
		txRfOutput,
		txCalTask,
		txCarrierAlarm,
		txDsssChipRate,
		txDsssSpreadFactor,
		txDsssCodeLength,
		txDsssCode,
		txDsssService,
		txDsssFixedModcod,
		txAcrLowSnrLimit,
		txVcmDesiredDrainTime,
		txVcmQueueLiveTime,
		txVcmCirMaxAlarm,
		txVcmCirMaxEvent,
		txHdrFixedModcod,
		txHdrSymbolRate,
		txHdrTotalMinSymbolRate,
		txHdrTotalMaxSymbolRate,
		txLevelMode,
		txBucFrequency,
		txFrequency,
		txLevelOffset,
		txOutput,
		txTestModulation,
		txSymbolRate,
		txVcmService,
		txVcmVlanId,
		txVcmRxChannel,
		txVcmCirMode,
		txVcmDesiredCir,
		txVcmMir,
		txVcmMinEsn0,
		txVcmMaxEsn0,
		txVcmFixedModcod,
		txVcmMinModcodAlarm,
		txVcmLowEsn0Alarm,
		txVcmLowEsn0Limit,
		txVcmMccChannelAlarm,
		txVcmDataAlarm,
		txVcmDataInactive,
		txVcmMccChannelEvent,
		txVcmMinModcodEvent,
		txVcmLowEsn0Event,
		txVcmDataEvent,
		txVcmId,
		totalEvents,
		eventLog
	}
	STATUS current
	DESCRIPTION "Description"
	::= { unitInfoGroups 1 }

END
