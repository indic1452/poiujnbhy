-- ********************************************************************
--
--  Datum Systems, Inc.
--  7211 E. Southern Ave, Suite 102
--  Mesa, 85209-2793
--  (480) 558-5500
--
--
--  This module provides authoritative definitions for Datum Systems'
--  enterprise-specific internal MIB.
--
--  This module will be extended, as required.
--
--  Generic naming is used to insure the customer does not access
--  the attributes of this MIB, unless instructed by technical
--  support.
--
--  Datum Systems reserves the right to make changes in
--  specification and other information contained in this document
--  without prior notice.  The reader should consult Datum Systems
--  to determine whether any such changes have been made.
--
--  In no event shall Datum Systems be liable for any incidental,
--  indirect, special, or consequential damages what so ever (including
--  but not limited to lost profits) arising out of or related to this
--  document or the information contained in it, even if Datum Systems
--  has been advised of, known, or should have known, the possibility
--  of such damages.
--
--  Datum Systems grants vendors, end-users, and other interested
--  parties a non-exclusive license to use this Specification in
--  connection with the management of Datum Systems' products.
--
--
--  Copyright June 2020-2025 Datum Systems, Inc.
--
-- ********************************************************************

--
-- Datum Systems, Inc. M7XC Class Modem MIB Module
-- Firmware Build: 3.0.8
--

DATUM-M7XC-MODEM-NOTIF-MIB DEFINITIONS ::= BEGIN

IMPORTS
        MODULE-IDENTITY, OBJECT-TYPE, NOTIFICATION-TYPE,
        Integer32, Unsigned32, IpAddress
            FROM SNMPv2-SMI
        DisplayString, DateAndTime
            FROM SNMPv2-TC
        MODULE-COMPLIANCE, AGENT-CAPABILITIES, OBJECT-GROUP, NOTIFICATION-GROUP
            FROM SNMPv2-CONF
        snmpTraps
            FROM SNMPv2-MIB
        datumModules, modems
            FROM DATUM-REG-MIB;

--
-- The module identification
--
m7xcNotifMibModule MODULE-IDENTITY
        LAST-UPDATED "202512092023Z"  -- December 9, 2025, 08:23
        ORGANIZATION "Datum Systems, Inc."
        CONTACT-INFO
            "Contact: Customer Support Group

              Postal: Datum Systems, Inc.
                      Customer Support Group
                      7211 E. Southern Ave, Suite 102
                      Mesa, AZ 85209-2793
                      US
                 Tel: +1 (480) 558-5500
                 Web: http://www.datumsystems.com/
               email: Support@DatumSystems.com"
        DESCRIPTION  "The Datum Systems, Inc. M7XC Satellite Modem Notification MIB."

        REVISION     "202512092023Z"  -- December 9, 2025, 08:23
        DESCRIPTION  "Full Auto Update Version."

    ::= { datumModules 6 }

-- Definition of MIB's root nodes
--
-- root for items in the modem notification MIB module
--
m7xcModem				OBJECT IDENTIFIER ::= { modems 4 }
m7xcModemNotifications	OBJECT IDENTIFIER ::= { m7xcModem 2 }
m7xcModemConformance	OBJECT IDENTIFIER ::= { m7xcModem 3 }

unitCompliance MODULE-COMPLIANCE
	STATUS      current
	DESCRIPTION "Specification requirement"
	MODULE	MANDATORY-GROUPS { m7xcObjectNotifGroup, m7xcTrapNotifGroup }
	::= { m7xcModemConformance 1 }

unitTrapCapabilities AGENT-CAPABILITIES
	PRODUCT-RELEASE "..."
	STATUS		current
	DESCRIPTION	"..."
	SUPPORTS	SNMPv2-MIB
	INCLUDES	{ snmpTraps }
	::= { m7xcModemNotifications 1 }

notifObjects			OBJECT IDENTIFIER ::= { m7xcModemNotifications 2 }
unitNotifObjects		OBJECT IDENTIFIER ::= { notifObjects 1 }
rxNotifObjects			OBJECT IDENTIFIER ::= { notifObjects 2 }
txNotifObjects			OBJECT IDENTIFIER ::= { notifObjects 3 }

notifTraps				OBJECT IDENTIFIER ::= { m7xcModemNotifications 4 }
unitNotifTraps			OBJECT IDENTIFIER ::= { notifTraps 1 }
unitNotifs				OBJECT IDENTIFIER ::= { unitNotifTraps 0 }
rxNotifTraps			OBJECT IDENTIFIER ::= { notifTraps 2 }
rxNotifs				OBJECT IDENTIFIER ::= { rxNotifTraps 0 }
txNotifTraps			OBJECT IDENTIFIER ::= { notifTraps 3 }
txNotifs				OBJECT IDENTIFIER ::= { txNotifTraps 0 }

eventCountInfo OBJECT-TYPE
	SYNTAX		Unsigned32
	UNITS		"1"
	MAX-ACCESS	accessible-for-notify
	STATUS		current
	DESCRIPTION "Event Count
			Oid=1.3.6.1.4.1.31968.3.1.4.2.2.1.1
			"
	::= { unitNotifObjects 1 }

unitStartupInfo OBJECT-TYPE
	SYNTAX		INTEGER {
		cold(0),
		warm(1),
		watchdog(2),
		reboot(3)
	}
	MAX-ACCESS	accessible-for-notify
	STATUS		current
	DESCRIPTION "Unit Startup, where:
			    0) 'Cold'
			    1) 'Warm'
			    2) 'WATCHDOG'
			    3) 'REBOOT'
			Oid=1.3.6.1.4.1.31968.3.1.4.2.2.1.2
			"
	::= { unitNotifObjects 2 }

unitStartupConfigInfo OBJECT-TYPE
	SYNTAX		Unsigned32
	UNITS		"1"
	MAX-ACCESS	accessible-for-notify
	STATUS		current
	DESCRIPTION "Unit Startup Configuration 0=Last, 1 to 99=Stored Configuration
			Oid=1.3.6.1.4.1.31968.3.1.4.2.2.1.3
			"
	::= { unitNotifObjects 3 }

unitFpgaLoadAlarmInfo OBJECT-TYPE
	SYNTAX		INTEGER {
		fpga1LoadFailed(0),
		fpga2LoadFailed(1),
		fpga3LoadFailed(2)
	}
	MAX-ACCESS	accessible-for-notify
	STATUS		current
	DESCRIPTION "Unit FPGA Load Failure Alarm, where:
			    0) 'FPGA 1 LOAD FAILED'
			    1) 'FPGA 2 LOAD FAILED'
			    2) 'FPGA 3 LOAD FAILED'
			Oid=1.3.6.1.4.1.31968.3.1.4.2.2.1.4
			"
	::= { unitNotifObjects 4 }

unitFileLoadAlarmInfo OBJECT-TYPE
	SYNTAX		INTEGER {
		fileTx02BinLoadFailed(0),
		fileTx05BinLoadFailed(1),
		fileTx10BinLoadFailed(2),
		fileTx15BinLoadFailed(3),
		fileTx20BinLoadFailed(4),
		fileTx25BinLoadFailed(5),
		fileTx30BinLoadFailed(6),
		fileTx35BinLoadFailed(7),
		fileTx40BinLoadFailed(8),
		fileCxBinLoadFailed(9)
	}
	MAX-ACCESS	accessible-for-notify
	STATUS		current
	DESCRIPTION "Unit File Load Failure Alarm, where:
			    0) 'FILE tx02.bin LOAD FAILED'
			    1) 'FILE tx05.bin LOAD FAILED'
			    2) 'FILE tx10.bin LOAD FAILED'
			    3) 'FILE tx15.bin LOAD FAILED'
			    4) 'FILE tx20.bin LOAD FAILED'
			    5) 'FILE tx25.bin LOAD FAILED'
			    6) 'FILE tx30.bin LOAD FAILED'
			    7) 'FILE tx35.bin LOAD FAILED'
			    8) 'FILE tx40.bin LOAD FAILED'
			    9) 'FILE cx.bin LOAD FAILED'
			Oid=1.3.6.1.4.1.31968.3.1.4.2.2.1.5
			"
	::= { unitNotifObjects 5 }

unitEepromLoadAlarmInfo OBJECT-TYPE
	SYNTAX		INTEGER {
		eepromTxIdLoadFailed(0),
		eepromUnitSnLoadFailed(1),
		eepromFeatureLoadFailed(2),
		eepromRxIdLoadFailed(3)
	}
	MAX-ACCESS	accessible-for-notify
	STATUS		current
	DESCRIPTION "Unit EEPROM Load Failure Alarm, where:
			    0) 'EEPROM Tx ID LOAD FAILED'
			    1) 'EEPROM Unit SN LOAD FAILED'
			    2) 'EEPROM FEATURE LOAD FAILED'
			    3) 'EEPROM Rx ID LOAD FAILED'
			Oid=1.3.6.1.4.1.31968.3.1.4.2.2.1.6
			"
	::= { unitNotifObjects 6 }

unitUncalibratedAlarmInfo OBJECT-TYPE
	SYNTAX		INTEGER {
		referenceUncalibrated(0),
		txDcOffsetUncalibrated(1),
		txLevelBalanceUncalibrated(2),
		txPhaseBalanceUncalibrated(3),
		txDelayBalanceUncalibrated(4),
		txLevelUncalibrated(5),
		txTiltUncalibrated(6),
		rxLevelBalanceUncalibrated(7),
		rxPhaseBalanceUncalibrated(8),
		rxEqualizerBalanceUncalibrated(9),
		rxLevelUncalibrated(10)
	}
	MAX-ACCESS	accessible-for-notify
	STATUS		current
	DESCRIPTION "Unit Calibration Load Alarm, where:
			    0) 'REFERENCE UNCALIBRATED'
			    1) 'Tx DC OFFSET UNCALIBRATED'
			    2) 'Tx LEVEL BALANCE UNCALIBRATED'
			    3) 'Tx PHASE BALANCE UNCALIBRATED'
			    4) 'Tx DELAY BALANCE UNCALIBRATED'
			    5) 'Tx LEVEL UNCALIBRATED'
			    6) 'Tx TILT UNCALIBRATED'
			    7) 'Rx LEVEL BALANCE UNCALIBRATED'
			    8) 'Rx PHASE BALANCE UNCALIBRATED'
			    9) 'Rx EQUALIZER BALANCE UNCALIBRATED'
			    10) 'Rx LEVEL UNCALIBRATED'
			Oid=1.3.6.1.4.1.31968.3.1.4.2.2.1.7
			"
	::= { unitNotifObjects 7 }

unitFactoryDefaultInfo OBJECT-TYPE
	SYNTAX		INTEGER {
		mgmtPortAddressSetToFactoryDefault(0),
		mgmtPortAddressSetToDhcp(1),
		unitNonvolatileConfigurationCorruptUsingFactoryDefault(2),
		unitNonvolatileConfigurationInvalidUsingFactoryDefault(3)
	}
	MAX-ACCESS	accessible-for-notify
	STATUS		current
	DESCRIPTION "Unit Factory Default Configuration, where:
			    0) 'MGMT PORT ADDRESS SET TO FACTORY DEFAULT'
			    1) 'MGMT PORT ADDRESS SET TO DHCP'
			    2) 'UNIT NONVOLATILE CONFIGURATION CORRUPT, USING FACTORY DEFAULT'
			    3) 'UNIT NONVOLATILE CONFIGURATION INVALID, USING FACTORY DEFAULT'
			Oid=1.3.6.1.4.1.31968.3.1.4.2.2.1.8
			"
	::= { unitNotifObjects 8 }

unitFirmwareUpdateInfo OBJECT-TYPE
	SYNTAX		INTEGER {
		firmwareUpdatedInPartitionA(0),
		firmwareUpdatedInPartitionB(1)
	}
	MAX-ACCESS	accessible-for-notify
	STATUS		current
	DESCRIPTION "Unit Firmware Update Partition, where:
			    0) 'Firmware Updated in Partition A'
			    1) 'Firmware Updated in Partition B'
			Oid=1.3.6.1.4.1.31968.3.1.4.2.2.1.9
			"
	::= { unitNotifObjects 9 }

unitHardwareAlarmInfo OBJECT-TYPE
	SYNTAX		INTEGER {
		unitHardwareOk(0),
		unitHardwareAlarm(1)
	}
	MAX-ACCESS	accessible-for-notify
	STATUS		current
	DESCRIPTION "Unit Hardware Alarm, where:
			    0) 'Unit Hardware Ok'
			    1) 'UNIT HARDWARE ALARM'
			Oid=1.3.6.1.4.1.31968.3.1.4.2.2.1.10
			"
	::= { unitNotifObjects 10 }

unitShutdownAlarmInfo OBJECT-TYPE
	SYNTAX		INTEGER {
		overTemperatureShutdownCleared(0),
		overTemperatureShutdown(1)
	}
	MAX-ACCESS	accessible-for-notify
	STATUS		current
	DESCRIPTION "Unit Over Temperature Shutdown Alarm, where:
			    0) 'Over Temperature Shutdown Cleared'
			    1) 'OVER TEMPERATURE SHUTDOWN'
			Oid=1.3.6.1.4.1.31968.3.1.4.2.2.1.11
			"
	::= { unitNotifObjects 11 }

unitCpuTemperatureAlarmInfo OBJECT-TYPE
	SYNTAX		INTEGER {
		unitCpuTemperatureOk(0),
		unitCpuOverTemperatureAlarm(1)
	}
	MAX-ACCESS	accessible-for-notify
	STATUS		current
	DESCRIPTION "Unit CPU Over Temperature Alarm, where:
			    0) 'Unit CPU Temperature Ok'
			    1) 'UNIT CPU OVER TEMPERATURE ALARM'
			Oid=1.3.6.1.4.1.31968.3.1.4.2.2.1.12
			"
	::= { unitNotifObjects 12 }

unitCpuTemperatureInfo OBJECT-TYPE
	SYNTAX		Integer32
	UNITS		"0.1 Degree C"
	MAX-ACCESS	accessible-for-notify
	STATUS		current
	DESCRIPTION "Unit CPU Temperature
			Oid=1.3.6.1.4.1.31968.3.1.4.2.2.1.13
			"
	::= { unitNotifObjects 13 }

unitReferenceInfo OBJECT-TYPE
	SYNTAX		INTEGER {
		referenceOcxoWarming(0),
		referenceAlarmFallback(1),
		referenceAlarmBadInput(2),
		referenceLocked(3),
		referenceOk(4)
	}
	MAX-ACCESS	accessible-for-notify
	STATUS		current
	DESCRIPTION "Unit Reference Status, where:
			    0) 'Reference OCXO Warming...'
			    1) 'Reference Alarm, Fallback'
			    2) 'Reference Alarm, Bad Input'
			    3) 'Reference Locked'
			    4) 'Reference Ok'
			Oid=1.3.6.1.4.1.31968.3.1.4.2.2.1.14
			"
	::= { unitNotifObjects 14 }

unitMgmtPortLinkInfo OBJECT-TYPE
	SYNTAX		INTEGER {
		mgmtPortLinkAlarm(0),
		mgmtPortAlarmNoDhcpIpAddress(1),
		mgmtPortLink10Mb(2),
		mgmtPortLink100Mb(3),
		mgmtPortLink1Gb(4)
	}
	MAX-ACCESS	accessible-for-notify
	STATUS		current
	DESCRIPTION "Unit Mgmt Port Link Status, where:
			    0) 'MGMT PORT LINK ALARM'
			    1) 'MGMT PORT ALARM, NO DHCP IP ADDRESS'
			    2) 'Mgmt Port Link 10 Mb'
			    3) 'Mgmt Port Link 100 Mb'
			    4) 'Mgmt Port Link 1 Gb'
			Oid=1.3.6.1.4.1.31968.3.1.4.2.2.1.15
			"
	::= { unitNotifObjects 15 }

unitDataPortLinkInfo OBJECT-TYPE
	SYNTAX		INTEGER {
		dataPortLinkAlarm(0),
		dataPortLink10Mb(1),
		dataPortLink100Mb(2),
		dataPortLink1Gb(3)
	}
	MAX-ACCESS	accessible-for-notify
	STATUS		current
	DESCRIPTION "Unit Data Port Link Status, where:
			    0) 'DATA PORT LINK ALARM'
			    1) 'Data Port Link 10 Mb'
			    2) 'Data Port Link 100 Mb'
			    3) 'Data Port Link 1 Gb'
			Oid=1.3.6.1.4.1.31968.3.1.4.2.2.1.16
			"
	::= { unitNotifObjects 16 }

unitInputPowerAlarmInfo OBJECT-TYPE
	SYNTAX		INTEGER {
		unitInputPowerOk(0),
		unitInputPowerAlarm(1)
	}
	MAX-ACCESS	accessible-for-notify
	STATUS		current
	DESCRIPTION "Unit Input Power Alarm, where:
			    0) 'Unit Input Power Ok'
			    1) 'UNIT INPUT POWER ALARM'
			Oid=1.3.6.1.4.1.31968.3.1.4.2.2.1.17
			"
	::= { unitNotifObjects 17 }

unitInputPowerVoltageInfo OBJECT-TYPE
	SYNTAX		Unsigned32
	UNITS		"0.1 V"
	MAX-ACCESS	accessible-for-notify
	STATUS		current
	DESCRIPTION "Unit Input Power Voltage
			Oid=1.3.6.1.4.1.31968.3.1.4.2.2.1.18
			"
	::= { unitNotifObjects 18 }

unitTestAlarmInfo OBJECT-TYPE
	SYNTAX		INTEGER {
		unitTestInactiveOk(0),
		unitTestActiveAlarm(1)
	}
	MAX-ACCESS	accessible-for-notify
	STATUS		current
	DESCRIPTION "Unit Test Active Alarm, where:
			    0) 'Unit Test Inactive, Ok'
			    1) 'UNIT TEST ACTIVE ALARM'
			Oid=1.3.6.1.4.1.31968.3.1.4.2.2.1.19
			"
	::= { unitNotifObjects 19 }

unitMonitorAlarmInfo OBJECT-TYPE
	SYNTAX		INTEGER {
		unitMonitorInactiveOk(0),
		unitMonitorActiveAlarm(1)
	}
	MAX-ACCESS	accessible-for-notify
	STATUS		current
	DESCRIPTION "Unit Monitor Input Alarm, where:
			    0) 'Unit Monitor Inactive, Ok'
			    1) 'UNIT MONITOR ACTIVE ALARM'
			Oid=1.3.6.1.4.1.31968.3.1.4.2.2.1.20
			"
	::= { unitNotifObjects 20 }

unitMonitorVoltageInfo OBJECT-TYPE
	SYNTAX		Unsigned32
	UNITS		"0.1 V"
	MAX-ACCESS	accessible-for-notify
	STATUS		current
	DESCRIPTION "Monitor Input Voltage
			Oid=1.3.6.1.4.1.31968.3.1.4.2.2.1.21
			"
	::= { unitNotifObjects 21 }

unitAuthenticationFailInfo OBJECT-TYPE
	SYNTAX		IpAddress
	MAX-ACCESS	accessible-for-notify
	STATUS		current
	DESCRIPTION "Unit Authentication Failure IP Address
			Oid=1.3.6.1.4.1.31968.3.1.4.2.2.1.22
			"
	::= { unitNotifObjects 22 }

unitAccessIpInfo OBJECT-TYPE
	SYNTAX		INTEGER {
		ssh(0),
		ip(1),
		snmp(2),
		http(3)
	}
	MAX-ACCESS	accessible-for-notify
	STATUS		current
	DESCRIPTION "Unit IP Access Port, where:
			    0) 'SSH'
			    1) 'IP'
			    2) 'SNMP'
			    3) 'HTTP'
			Oid=1.3.6.1.4.1.31968.3.1.4.2.2.1.23
			"
	::= { unitNotifObjects 23 }

unitAccessIpAddressInfo OBJECT-TYPE
	SYNTAX		IpAddress
	MAX-ACCESS	accessible-for-notify
	STATUS		current
	DESCRIPTION "Unit IP Access IP Address
			Oid=1.3.6.1.4.1.31968.3.1.4.2.2.1.24
			"
	::= { unitNotifObjects 24 }

unitAccessPortInfo OBJECT-TYPE
	SYNTAX		INTEGER {
		rs232(0),
		mcc(1)
	}
	MAX-ACCESS	accessible-for-notify
	STATUS		current
	DESCRIPTION "Unit Port Access Port, where:
			    0) 'RS-232'
			    1) 'MCC'
			Oid=1.3.6.1.4.1.31968.3.1.4.2.2.1.25
			"
	::= { unitNotifObjects 25 }

unitAccessPortAddressInfo OBJECT-TYPE
	SYNTAX		Unsigned32
	UNITS		"1"
	MAX-ACCESS	accessible-for-notify
	STATUS		current
	DESCRIPTION "Unit Port Access Address
			Oid=1.3.6.1.4.1.31968.3.1.4.2.2.1.26
			"
	::= { unitNotifObjects 26 }

unitTamperAlarmInfo OBJECT-TYPE
	SYNTAX		INTEGER {
		tamperOk(0),
		tamperAlarm(1)
	}
	MAX-ACCESS	accessible-for-notify
	STATUS		current
	DESCRIPTION "Unit Tamper Alarm, where:
			    0) 'Tamper Ok'
			    1) 'TAMPER ALARM'
			Oid=1.3.6.1.4.1.31968.3.1.4.2.2.1.27
			"
	::= { unitNotifObjects 27 }

unitTrialAlarmInfo OBJECT-TYPE
	SYNTAX		INTEGER {
		trialOk(0),
		trialExpired(1),
		trialExpiresInLessThan24Hours(2),
		trialExpiresInLessThan7Days(3)
	}
	MAX-ACCESS	accessible-for-notify
	STATUS		current
	DESCRIPTION "Unit Trial Activation, where:
			    0) 'Trial Ok'
			    1) 'TRIAL EXPIRED'
			    2) 'TRIAL EXPIRES IN < 24 HOURS'
			    3) 'TRIAL EXPIRES IN < 7 DAYS'
			Oid=1.3.6.1.4.1.31968.3.1.4.2.2.1.28
			"
	::= { unitNotifObjects 28 }

unitDhcpAcquiredIpAddressInfo OBJECT-TYPE
	SYNTAX		IpAddress
	MAX-ACCESS	accessible-for-notify
	STATUS		current
	DESCRIPTION "Unit DHCP Acquired IP Address
			Oid=1.3.6.1.4.1.31968.3.1.4.2.2.1.29
			"
	::= { unitNotifObjects 29 }

unitDateTimeInfo OBJECT-TYPE
	SYNTAX		INTEGER {
		dateTimeNotSet(0),
		dateTimeSetByNtpServer(1)
	}
	MAX-ACCESS	accessible-for-notify
	STATUS		current
	DESCRIPTION "Unit Date/Time Event, where:
			    0) 'DATE/TIME NOT SET'
			    1) 'Date/Time Set By NTP Server'
			Oid=1.3.6.1.4.1.31968.3.1.4.2.2.1.30
			"
	::= { unitNotifObjects 30 }

unitConfigChangedInfo OBJECT-TYPE
	SYNTAX		INTEGER {
		configurationModifiedViaSsh(0),
		configurationModifiedViaRs232(1),
		configurationModifiedViaMcc(2),
		configurationModifiedViaIp(3),
		configurationModifiedViaSnmp(4),
		configurationModifiedViaHttp(5),
		configurationModifiedViaAcu(6)
	}
	MAX-ACCESS	accessible-for-notify
	STATUS		current
	DESCRIPTION "Unit Configuration Changed From Port, where:
			    0) 'Configuration Modified Via SSH'
			    1) 'Configuration Modified Via RS-232'
			    2) 'Configuration Modified Via MCC'
			    3) 'Configuration Modified Via IP'
			    4) 'Configuration Modified Via SNMP'
			    5) 'Configuration Modified Via HTTP'
			    6) 'Configuration Modified Via ACU'
			Oid=1.3.6.1.4.1.31968.3.1.4.2.2.1.31
			"
	::= { unitNotifObjects 31 }

unitConfigStoredInfo OBJECT-TYPE
	SYNTAX		Unsigned32
	UNITS		"1"
	MAX-ACCESS	accessible-for-notify
	STATUS		current
	DESCRIPTION "Unit Configuration Stored To 0=Factory Default, 1..99=Unit Location, 100=Downloaded File
			Oid=1.3.6.1.4.1.31968.3.1.4.2.2.1.32
			"
	::= { unitNotifObjects 32 }

unitConfigRestoredInfo OBJECT-TYPE
	SYNTAX		Unsigned32
	UNITS		"1"
	MAX-ACCESS	accessible-for-notify
	STATUS		current
	DESCRIPTION "Unit Configuration Restored From 0=Factory Default, 1..99=Unit Location, 100=Uploaded File
			Oid=1.3.6.1.4.1.31968.3.1.4.2.2.1.33
			"
	::= { unitNotifObjects 33 }

unitRtcBatteryAlarmInfo OBJECT-TYPE
	SYNTAX		INTEGER {
		unitRtcBatteryOk(0),
		unitRtcBatteryAlarm(1)
	}
	MAX-ACCESS	accessible-for-notify
	STATUS		current
	DESCRIPTION "Unit RTC Battery Alarm, where:
			    0) 'Unit RTC Battery Ok'
			    1) 'UNIT RTC BATTERY ALARM'
			Oid=1.3.6.1.4.1.31968.3.1.4.2.2.1.34
			"
	::= { unitNotifObjects 34 }

unitRtcBatteryVoltageInfo OBJECT-TYPE
	SYNTAX		Unsigned32
	UNITS		"0.01 V"
	MAX-ACCESS	accessible-for-notify
	STATUS		current
	DESCRIPTION "Unit RTC Battery Voltage
			Oid=1.3.6.1.4.1.31968.3.1.4.2.2.1.35
			"
	::= { unitNotifObjects 35 }

unitAcuInfo OBJECT-TYPE
	SYNTAX		INTEGER {
		error(0),
		txMutedIpConnectionAlarm(1),
		ipConnectionAlarm(2),
		txMutedKeepAliveAlarm(3),
		keepAliveAlarm(4),
		txMutedIpConnectionAlarmReport(5),
		ipConnectionAlarmReport(6),
		txMutedKeepAliveAlarmReport(7),
		keepAliveAlarmReport(8),
		txMutedWaitingForAcu(9),
		off(10),
		modemMayTransmit(11),
		cableUnwrap(12),
		blockageZone(13),
		rfHazardZone(14),
		sidelobeCheck(15),
		elevationLimit(16),
		azSkewLimit(17),
		gyroCap(18),
		acuSearchState(19),
		rssiBelowThreshold(20),
		initializing(21),
		lnbVoltageError(22),
		bucVoltageError(23),
		rfConfigurationError(24),
		rfCommunicationError(25),
		onGround(26),
		geographicRestriction(27),
		hardwareMuteSwitch(28),
		blockageWarning(29),
		rfAcuResourcesBusy(30),
		acuMutedByModem(31),
		peaking(32),
		pendingOperatorAuthorization(33),
		solarOutage(34),
		stabilisationError(35),
		motorErrorFailure(36),
		encoderErrorFailure(37),
		sensorErrorFailure(38),
		acuCommunicationErrorFailure(39),
		powerError(40),
		acuOutOfCalibration(41)
	}
	MAX-ACCESS	accessible-for-notify
	STATUS		current
	DESCRIPTION "Unit ACU Status, where:
			    0) 'ERROR'
			    1) 'Tx MUTED, IP CONNECTION ALARM'
			    2) 'IP CONNECTION ALARM'
			    3) 'Tx MUTED, KEEP ALIVE ALARM'
			    4) 'KEEP ALIVE ALARM'
			    5) 'Tx Muted, IP Connection Alarm Report'
			    6) 'IP Connection Alarm Report'
			    7) 'Tx Muted, Keep Alive Alarm Report'
			    8) 'Keep Alive Alarm Report'
			    9) 'Tx Muted, Waiting For ACU...'
			    10) 'Off'
			    11) 'Modem May Transmit'
			    12) 'Cable Unwrap'
			    13) 'Blockage Zone'
			    14) 'RF Hazard Zone'
			    15) 'Sidelobe Check'
			    16) 'Elevation Limit'
			    17) 'AZ/SKEW Limit'
			    18) 'Gyro Cap'
			    19) 'ACU Search State'
			    20) 'RSSI Below Threshold'
			    21) 'Initializing'
			    22) 'LNB Voltage Error'
			    23) 'BUC Voltage Error'
			    24) 'RF Configuration Error'
			    25) 'RF Communication Error'
			    26) 'On Ground'
			    27) 'Geographic Restriction'
			    28) 'Hardware Mute Switch'
			    29) 'Blockage Warning'
			    30) 'RF ACU Resources Busy'
			    31) 'ACU Muted by Modem'
			    32) 'Peaking'
			    33) 'Pending Operator Authorization'
			    34) 'Solar Outage'
			    35) 'Stabilisation Error'
			    36) 'Motor Error/Failure'
			    37) 'Encoder Error/Failure'
			    38) 'Sensor Error/Failure'
			    39) 'ACU Communication Error/Failure'
			    40) 'Power Error'
			    41) 'ACU Out of Calibration'
			Oid=1.3.6.1.4.1.31968.3.1.4.2.2.1.36
			"
	::= { unitNotifObjects 36 }

rxChannelInfo OBJECT-TYPE
	SYNTAX		Unsigned32
	UNITS		"1"
	MAX-ACCESS	accessible-for-notify
	STATUS		current
	DESCRIPTION "Rx Channel Number
			Oid=1.3.6.1.4.1.31968.3.1.4.2.2.2.1
			"
	::= { rxNotifObjects 1 }

rxWaveformInfo OBJECT-TYPE
	SYNTAX		INTEGER {
		off(0),
		dvbS2x(1),
		mil165bDvbS2x(2),
		dvbS2xVcm(3),
		dvbS2xWSmartCarrier(4),
		ldpcGen2(5),
		ldpcGen2WSmartCarrier(6),
		ldpcGen2WSmartCarrierHub(7),
		segmentedLdpcGen2(8),
		spectrumAnalyzer(9),
		calibration(10)
	}
	MAX-ACCESS	accessible-for-notify
	STATUS		current
	DESCRIPTION "Rx Waveform, where:
			    0) 'Off'
			    1) 'DVB-S2X'
			    2) 'MIL 165B DVB-S2X'
			    3) 'DVB-S2X VCM'
			    4) 'DVB-S2X w/Smart Carrier'
			    5) 'LDPC-Gen2'
			    6) 'LDPC-Gen2 w/Smart Carrier'
			    7) 'LDPC-Gen2 w/Smart Carrier Hub'
			    8) 'Segmented LDPC-Gen2'
			    9) 'Spectrum Analyzer'
			    10) 'Calibration'
			Oid=1.3.6.1.4.1.31968.3.1.4.2.2.2.2
			"
	::= { rxNotifObjects 2 }

rxEchoLockAlarmInfo OBJECT-TYPE
	SYNTAX		INTEGER {
		echoLockOk(0),
		echoLockAlarm(1)
	}
	MAX-ACCESS	accessible-for-notify
	STATUS		current
	DESCRIPTION "Rx Echo Lock Alarm, where:
			    0) 'Echo Lock Ok'
			    1) 'ECHO LOCK ALARM'
			Oid=1.3.6.1.4.1.31968.3.1.4.2.2.2.3
			"
	::= { rxNotifObjects 3 }

rxEchoLevelAlarmInfo OBJECT-TYPE
	SYNTAX		INTEGER {
		echoLevelOk(0),
		echoLevelImbalanceAlarm(1)
	}
	MAX-ACCESS	accessible-for-notify
	STATUS		current
	DESCRIPTION "Rx Echo Level Imbalance Alarm, where:
			    0) 'Echo Level Ok'
			    1) 'ECHO LEVEL IMBALANCE ALARM'
			Oid=1.3.6.1.4.1.31968.3.1.4.2.2.2.4
			"
	::= { rxNotifObjects 4 }

rxEchoLevelImbalanceInfo OBJECT-TYPE
	SYNTAX		Integer32
	UNITS		"0.01 dB"
	MAX-ACCESS	accessible-for-notify
	STATUS		current
	DESCRIPTION "Rx Echo Level Imbalance
			Oid=1.3.6.1.4.1.31968.3.1.4.2.2.2.5
			"
	::= { rxNotifObjects 5 }

rxEchoOffsetAlarmInfo OBJECT-TYPE
	SYNTAX		INTEGER {
		echoOffsetOk(0),
		echoOffsetImbalanceAlarm(1)
	}
	MAX-ACCESS	accessible-for-notify
	STATUS		current
	DESCRIPTION "Rx Echo Frequency Offset Imbalance Alarm, where:
			    0) 'Echo offset Ok'
			    1) 'ECHO OFFSET IMBALANCE ALARM'
			Oid=1.3.6.1.4.1.31968.3.1.4.2.2.2.6
			"
	::= { rxNotifObjects 6 }

rxEchoOffsetImbalanceInfo OBJECT-TYPE
	SYNTAX		Integer32
	UNITS		"1 Hz"
	MAX-ACCESS	accessible-for-notify
	STATUS		current
	DESCRIPTION "Rx Echo Frequency Offset Imbalance
			Oid=1.3.6.1.4.1.31968.3.1.4.2.2.2.7
			"
	::= { rxNotifObjects 7 }

rxLockInfo OBJECT-TYPE
	SYNTAX		INTEGER {
		off(0),
		unlocked(1),
		locked(2),
		lockedDataIdle(3),
		lockedDataLive(4),
		lockedDataUnbonded(5)
	}
	MAX-ACCESS	accessible-for-notify
	STATUS		current
	DESCRIPTION "Rx Lock, where:
			    0) 'Off'
			    1) 'UNLOCKED'
			    2) 'Locked'
			    3) 'Locked, Data Idle'
			    4) 'Locked, Data Live'
			    5) 'Locked, DATA UNBONDED'
			Oid=1.3.6.1.4.1.31968.3.1.4.2.2.2.8
			"
	::= { rxNotifObjects 8 }

rxLowMarginAlarmInfo OBJECT-TYPE
	SYNTAX		INTEGER {
		marginOk(0),
		lowMarginAlarm(1)
	}
	MAX-ACCESS	accessible-for-notify
	STATUS		current
	DESCRIPTION "Rx Low Es/N0 Margin Alarm, where:
			    0) 'Margin Ok'
			    1) 'LOW MARGIN ALARM'
			Oid=1.3.6.1.4.1.31968.3.1.4.2.2.2.9
			"
	::= { rxNotifObjects 9 }

rxLowMarginInfo OBJECT-TYPE
	SYNTAX		Integer32
	UNITS		"0.01 dB"
	MAX-ACCESS	accessible-for-notify
	STATUS		current
	DESCRIPTION "Rx Margin
			Oid=1.3.6.1.4.1.31968.3.1.4.2.2.2.10
			"
	::= { rxNotifObjects 10 }

rxLowLevelAlarmInfo OBJECT-TYPE
	SYNTAX		INTEGER {
		levelOk(0),
		lowLevelAlarm(1)
	}
	MAX-ACCESS	accessible-for-notify
	STATUS		current
	DESCRIPTION "Rx Low Level Alarm, where:
			    0) 'Level Ok'
			    1) 'LOW LEVEL ALARM'
			Oid=1.3.6.1.4.1.31968.3.1.4.2.2.2.11
			"
	::= { rxNotifObjects 11 }

rxLowLevelInfo OBJECT-TYPE
	SYNTAX		Integer32
	UNITS		"0.01 dBm"
	MAX-ACCESS	accessible-for-notify
	STATUS		current
	DESCRIPTION "Rx Level
			Oid=1.3.6.1.4.1.31968.3.1.4.2.2.2.12
			"
	::= { rxNotifObjects 12 }

rxMaxAgcAlarmInfo OBJECT-TYPE
	SYNTAX		INTEGER {
		agcOk(0),
		agcHardwareMaximumLimitAlarm(1)
	}
	MAX-ACCESS	accessible-for-notify
	STATUS		current
	DESCRIPTION "Rx Input Maximum AGC Overload Alarm, where:
			    0) 'AGC Ok'
			    1) 'AGC HARDWARE MAXIMUM LIMIT ALARM'
			Oid=1.3.6.1.4.1.31968.3.1.4.2.2.2.13
			"
	::= { rxNotifObjects 13 }

rxLnbPowerAlarmInfo OBJECT-TYPE
	SYNTAX		INTEGER {
		lnbPowerOk(0),
		lnbPowerAlarm(1)
	}
	MAX-ACCESS	accessible-for-notify
	STATUS		current
	DESCRIPTION "Rx LNB Power Alarm, where:
			    0) 'LNB Power Ok'
			    1) 'LNB POWER ALARM'
			Oid=1.3.6.1.4.1.31968.3.1.4.2.2.2.14
			"
	::= { rxNotifObjects 14 }

rxLnbPowerVoltageInfo OBJECT-TYPE
	SYNTAX		Integer32
	UNITS		"0.01 V"
	MAX-ACCESS	accessible-for-notify
	STATUS		current
	DESCRIPTION "Rx LNB Power Voltage
			Oid=1.3.6.1.4.1.31968.3.1.4.2.2.2.15
			"
	::= { rxNotifObjects 15 }

rxLnbPowerCurrentInfo OBJECT-TYPE
	SYNTAX		Integer32
	UNITS		"1 mA"
	MAX-ACCESS	accessible-for-notify
	STATUS		current
	DESCRIPTION "Rx LNB Power Current
			Oid=1.3.6.1.4.1.31968.3.1.4.2.2.2.16
			"
	::= { rxNotifObjects 16 }

rxTransecInfo OBJECT-TYPE
	SYNTAX		INTEGER {
		notInstalled(0),
		temperatureAlarm(1),
		hardwareAlarm(2),
		selfTestFailure(3),
		notOperational(4),
		coIdentifierKeysZeroizedLog(5),
		keyNotInitializedLog(6),
		dataNotEncryptedLog(7),
		errorKeyIndexInvalidLog(8),
		errorKeyIndexExpiredLog(9),
		keyMismatchLog(10),
		dataEncryptedLog(11),
		coIdentifierKeysZeroized(12),
		keyNotInitialized(13),
		dataNotEncrypted(14),
		errorKeyIndexInvalid(15),
		errorKeyIndexExpired(16),
		keyMismatch(17),
		dataEncrypted(18),
		alarmNotInstalled(19),
		alarmTemperatureAlarm(20),
		alarmHardwareAlarm(21),
		alarmSelfTestFailure(22),
		alarmNotOperational(23),
		alarmCoIdentifierKeysZeroizedLog(24),
		alarmKeyNotInitializedLog(25),
		alarmDataNotEncryptedLog(26),
		alarmErrorKeyIndexInvalidLog(27),
		alarmErrorKeyIndexExpiredLog(28),
		alarmKeyMismatchLog(29),
		alarmDataEncryptedLog(30),
		alarmCoIdentifierKeysZeroized(31),
		alarmKeyNotInitialized(32),
		alarmDataNotEncrypted(33),
		alarmErrorKeyIndexInvalid(34),
		alarmErrorKeyIndexExpired(35),
		alarmKeyMismatch(36),
		alarmDataEncrypted(37)
	}
	MAX-ACCESS	accessible-for-notify
	STATUS		current
	DESCRIPTION "Rx TRANSEC, where:
			    0) 'Not Installed'
			    1) 'TEMPERATURE ALARM'
			    2) 'HARDWARE ALARM'
			    3) 'SELF TEST FAILURE'
			    4) 'NOT OPERATIONAL'
			    5) 'CO Identifier/Keys Zeroized, Log'
			    6) 'KEY NOT INITIALIZED, Log'
			    7) 'DATA NOT ENCRYPTED, Log'
			    8) 'ERROR, KEY INDEX INVALID, Log'
			    9) 'ERROR, KEY INDEX EXPIRED, Log'
			    10) 'KEY MISMATCH, Log'
			    11) 'Data Encrypted, Log'
			    12) 'CO Identifier/Keys Zeroized'
			    13) 'KEY NOT INITIALIZED'
			    14) 'DATA NOT ENCRYPTED'
			    15) 'ERROR, KEY INDEX INVALID'
			    16) 'ERROR, KEY INDEX EXPIRED'
			    17) 'KEY MISMATCH'
			    18) 'Data Encrypted'
			    19) 'ALARM: Not Installed'
			    20) 'ALARM: TEMPERATURE ALARM'
			    21) 'ALARM: HARDWARE ALARM'
			    22) 'ALARM: SELF TEST FAILURE'
			    23) 'ALARM: NOT OPERATIONAL'
			    24) 'ALARM: CO Identifier/Keys Zeroized, Log'
			    25) 'ALARM: KEY NOT INITIALIZED, Log'
			    26) 'ALARM: DATA NOT ENCRYPTED, Log'
			    27) 'ALARM: ERROR, KEY INDEX INVALID, Log'
			    28) 'ALARM: ERROR, KEY INDEX EXPIRED, Log'
			    29) 'ALARM: KEY MISMATCH, Log'
			    30) 'ALARM: Data Encrypted, Log'
			    31) 'ALARM: CO Identifier/Keys Zeroized'
			    32) 'ALARM: KEY NOT INITIALIZED'
			    33) 'ALARM: DATA NOT ENCRYPTED'
			    34) 'ALARM: ERROR, KEY INDEX INVALID'
			    35) 'ALARM: ERROR, KEY INDEX EXPIRED'
			    36) 'ALARM: KEY MISMATCH'
			    37) 'ALARM: Data Encrypted'
			Oid=1.3.6.1.4.1.31968.3.1.4.2.2.2.17
			"
	::= { rxNotifObjects 17 }

rxModcodDvbInfo OBJECT-TYPE
	SYNTAX		INTEGER {
		qpsk14Normal(4),
		qpsk14NormalWPilot(5),
		qpsk14Short(6),
		qpsk14ShortWPilot(7),
		qpsk13Normal(8),
		qpsk13NormalWPilot(9),
		qpsk13Short(10),
		qpsk13ShortWPilot(11),
		qpsk25Normal(12),
		qpsk25NormalWPilot(13),
		qpsk25Short(14),
		qpsk25ShortWPilot(15),
		qpsk12Normal(16),
		qpsk12NormalWPilot(17),
		qpsk12Short(18),
		qpsk12ShortWPilot(19),
		qpsk35Normal(20),
		qpsk35NormalWPilot(21),
		qpsk35Short(22),
		qpsk35ShortWPilot(23),
		qpsk23Normal(24),
		qpsk23NormalWPilot(25),
		qpsk23Short(26),
		qpsk23ShortWPilot(27),
		qpsk34Normal(28),
		qpsk34NormalWPilot(29),
		qpsk34Short(30),
		qpsk34ShortWPilot(31),
		qpsk45Normal(32),
		qpsk45NormalWPilot(33),
		qpsk45Short(34),
		qpsk45ShortWPilot(35),
		qpsk56Normal(36),
		qpsk56NormalWPilot(37),
		qpsk56Short(38),
		qpsk56ShortWPilot(39),
		qpsk89Normal(40),
		qpsk89NormalWPilot(41),
		qpsk89Short(42),
		qpsk89ShortWPilot(43),
		qpsk910Normal(44),
		qpsk910NormalWPilot(45),
		n8psk35Normal(48),
		n8psk35NormalWPilot(49),
		n8psk35Short(50),
		n8psk35ShortWPilot(51),
		n8psk23Normal(52),
		n8psk23NormalWPilot(53),
		n8psk23Short(54),
		n8psk23ShortWPilot(55),
		n8psk34Normal(56),
		n8psk34NormalWPilot(57),
		n8psk34Short(58),
		n8psk34ShortWPilot(59),
		n8psk56Normal(60),
		n8psk56NormalWPilot(61),
		n8psk56Short(62),
		n8psk56ShortWPilot(63),
		n8psk89Normal(64),
		n8psk89NormalWPilot(65),
		n8psk89Short(66),
		n8psk89ShortWPilot(67),
		n8psk910Normal(68),
		n8psk910NormalWPilot(69),
		n16apsk23Normal(72),
		n16apsk23NormalWPilot(73),
		n16apsk23Short(74),
		n16apsk23ShortWPilot(75),
		n16apsk34Normal(76),
		n16apsk34NormalWPilot(77),
		n16apsk34Short(78),
		n16apsk34ShortWPilot(79),
		n16apsk45Normal(80),
		n16apsk45NormalWPilot(81),
		n16apsk45Short(82),
		n16apsk45ShortWPilot(83),
		n16apsk56Normal(84),
		n16apsk56NormalWPilot(85),
		n16apsk56Short(86),
		n16apsk56ShortWPilot(87),
		n16apsk89Normal(88),
		n16apsk89NormalWPilot(89),
		n16apsk89Short(90),
		n16apsk89ShortWPilot(91),
		n16apsk910Normal(92),
		n16apsk910NormalWPilot(93),
		n32apsk34Normal(96),
		n32apsk34NormalWPilot(97),
		n32apsk34Short(98),
		n32apsk34ShortWPilot(99),
		n32apsk45Normal(100),
		n32apsk45NormalWPilot(101),
		n32apsk45Short(102),
		n32apsk45ShortWPilot(103),
		n32apsk56Normal(104),
		n32apsk56NormalWPilot(105),
		n32apsk56Short(106),
		n32apsk56ShortWPilot(107),
		n32apsk89Normal(108),
		n32apsk89NormalWPilot(109),
		n32apsk89Short(110),
		n32apsk89ShortWPilot(111),
		n32apsk910Normal(112),
		n32apsk910NormalWPilot(113),
		qpsk1345Normal(132),
		qpsk1345NormalWPilot(133),
		qpsk920Normal(134),
		qpsk920NormalWPilot(135),
		qpsk1120Normal(136),
		qpsk1120NormalWPilot(137),
		n8apsk59LNormal(138),
		n8apsk59LNormalWPilot(139),
		n8apsk2645LNormal(140),
		n8apsk2645LNormalWPilot(141),
		n8psk2336Normal(142),
		n8psk2336NormalWPilot(143),
		n8psk2536Normal(144),
		n8psk2536NormalWPilot(145),
		n8psk1318Normal(146),
		n8psk1318NormalWPilot(147),
		n16apsk12LNormal(148),
		n16apsk12LNormalWPilot(149),
		n16apsk815LNormal(150),
		n16apsk815LNormalWPilot(151),
		n16apsk59LNormal(152),
		n16apsk59LNormalWPilot(153),
		n16apsk2645Normal(154),
		n16apsk2645NormalWPilot(155),
		n16apsk35Normal(156),
		n16apsk35NormalWPilot(157),
		n16apsk35LNormal(158),
		n16apsk35LNormalWPilot(159),
		n16apsk2845Normal(160),
		n16apsk2845NormalWPilot(161),
		n16apsk2336Normal(162),
		n16apsk2336NormalWPilot(163),
		n16apsk23LNormal(164),
		n16apsk23LNormalWPilot(165),
		n16apsk2536Normal(166),
		n16apsk2536NormalWPilot(167),
		n16apsk1318Normal(168),
		n16apsk1318NormalWPilot(169),
		n16apsk79Normal(170),
		n16apsk79NormalWPilot(171),
		n16apsk7790Normal(172),
		n16apsk7790NormalWPilot(173),
		n32apsk23LNormal(174),
		n32apsk23LNormalWPilot(175),
		n32apsk3245Normal(178),
		n32apsk3245NormalWPilot(179),
		n32apsk1115Normal(180),
		n32apsk1115NormalWPilot(181),
		n32apsk79Normal(182),
		n32apsk79NormalWPilot(183),
		n64apsk3245LNormal(184),
		n64apsk3245LNormalWPilot(185),
		n64apsk1115Normal(186),
		n64apsk1115NormalWPilot(187),
		n64apsk79Normal(190),
		n64apsk79NormalWPilot(191),
		n64apsk45Normal(194),
		n64apsk45NormalWPilot(195),
		n64apsk56Normal(198),
		n64apsk56NormalWPilot(199),
		n128apsk34Normal(200),
		n128apsk34NormalWPilot(201),
		n128apsk79Normal(202),
		n128apsk79NormalWPilot(203),
		n256apsk2945LNormal(204),
		n256apsk2945LNormalWPilot(205),
		n256apsk23LNormal(206),
		n256apsk23LNormalWPilot(207),
		n256apsk3145LNormal(208),
		n256apsk3145LNormalWPilot(209),
		n256apsk3245Normal(210),
		n256apsk3245NormalWPilot(211),
		n256apsk1115LNormal(212),
		n256apsk1115LNormalWPilot(213),
		n256apsk34Normal(214),
		n256apsk34NormalWPilot(215),
		qpsk1145Short(216),
		qpsk1145ShortWPilot(217),
		qpsk415Short(218),
		qpsk415ShortWPilot(219),
		qpsk1445Short(220),
		qpsk1445ShortWPilot(221),
		qpsk715Short(222),
		qpsk715ShortWPilot(223),
		qpsk815Short(224),
		qpsk815ShortWPilot(225),
		qpsk3245Short(226),
		qpsk3245ShortWPilot(227),
		n8psk715Short(228),
		n8psk715ShortWPilot(229),
		n8psk815Short(230),
		n8psk815ShortWPilot(231),
		n8psk2645Short(232),
		n8psk2645ShortWPilot(233),
		n8psk3245Short(234),
		n8psk3245ShortWPilot(235),
		n16apsk715Short(236),
		n16apsk715ShortWPilot(237),
		n16apsk815Short(238),
		n16apsk815ShortWPilot(239),
		n16apsk2645Short(240),
		n16apsk2645ShortWPilot(241),
		n16apsk35Short(242),
		n16apsk35ShortWPilot(243),
		n16apsk3245Short(244),
		n16apsk3245ShortWPilot(245),
		n32apsk23Short(246),
		n32apsk23ShortWPilot(247),
		n32apsk3245Short(248),
		n32apsk3245ShortWPilot(249),
		unlocked(256)
	}
	MAX-ACCESS	accessible-for-notify
	STATUS		current
	DESCRIPTION "Rx DVB-S2X ModCod, where:
			    4) 'QPSK 1/4 Normal'
			    5) 'QPSK 1/4 Normal w/Pilot'
			    6) 'QPSK 1/4 Short'
			    7) 'QPSK 1/4 Short w/Pilot'
			    8) 'QPSK 1/3 Normal'
			    9) 'QPSK 1/3 Normal w/Pilot'
			    10) 'QPSK 1/3 Short'
			    11) 'QPSK 1/3 Short w/Pilot'
			    12) 'QPSK 2/5 Normal'
			    13) 'QPSK 2/5 Normal w/Pilot'
			    14) 'QPSK 2/5 Short'
			    15) 'QPSK 2/5 Short w/Pilot'
			    16) 'QPSK 1/2 Normal'
			    17) 'QPSK 1/2 Normal w/Pilot'
			    18) 'QPSK 1/2 Short'
			    19) 'QPSK 1/2 Short w/Pilot'
			    20) 'QPSK 3/5 Normal'
			    21) 'QPSK 3/5 Normal w/Pilot'
			    22) 'QPSK 3/5 Short'
			    23) 'QPSK 3/5 Short w/Pilot'
			    24) 'QPSK 2/3 Normal'
			    25) 'QPSK 2/3 Normal w/Pilot'
			    26) 'QPSK 2/3 Short'
			    27) 'QPSK 2/3 Short w/Pilot'
			    28) 'QPSK 3/4 Normal'
			    29) 'QPSK 3/4 Normal w/Pilot'
			    30) 'QPSK 3/4 Short'
			    31) 'QPSK 3/4 Short w/Pilot'
			    32) 'QPSK 4/5 Normal'
			    33) 'QPSK 4/5 Normal w/Pilot'
			    34) 'QPSK 4/5 Short'
			    35) 'QPSK 4/5 Short w/Pilot'
			    36) 'QPSK 5/6 Normal'
			    37) 'QPSK 5/6 Normal w/Pilot'
			    38) 'QPSK 5/6 Short'
			    39) 'QPSK 5/6 Short w/Pilot'
			    40) 'QPSK 8/9 Normal'
			    41) 'QPSK 8/9 Normal w/Pilot'
			    42) 'QPSK 8/9 Short'
			    43) 'QPSK 8/9 Short w/Pilot'
			    44) 'QPSK 9/10 Normal'
			    45) 'QPSK 9/10 Normal w/Pilot'
			    48) '8PSK 3/5 Normal'
			    49) '8PSK 3/5 Normal w/Pilot'
			    50) '8PSK 3/5 Short'
			    51) '8PSK 3/5 Short w/Pilot'
			    52) '8PSK 2/3 Normal'
			    53) '8PSK 2/3 Normal w/Pilot'
			    54) '8PSK 2/3 Short'
			    55) '8PSK 2/3 Short w/Pilot'
			    56) '8PSK 3/4 Normal'
			    57) '8PSK 3/4 Normal w/Pilot'
			    58) '8PSK 3/4 Short'
			    59) '8PSK 3/4 Short w/Pilot'
			    60) '8PSK 5/6 Normal'
			    61) '8PSK 5/6 Normal w/Pilot'
			    62) '8PSK 5/6 Short'
			    63) '8PSK 5/6 Short w/Pilot'
			    64) '8PSK 8/9 Normal'
			    65) '8PSK 8/9 Normal w/Pilot'
			    66) '8PSK 8/9 Short'
			    67) '8PSK 8/9 Short w/Pilot'
			    68) '8PSK 9/10 Normal'
			    69) '8PSK 9/10 Normal w/Pilot'
			    72) '16APSK 2/3 Normal'
			    73) '16APSK 2/3 Normal w/Pilot'
			    74) '16APSK 2/3 Short'
			    75) '16APSK 2/3 Short w/Pilot'
			    76) '16APSK 3/4 Normal'
			    77) '16APSK 3/4 Normal w/Pilot'
			    78) '16APSK 3/4 Short'
			    79) '16APSK 3/4 Short w/Pilot'
			    80) '16APSK 4/5 Normal'
			    81) '16APSK 4/5 Normal w/Pilot'
			    82) '16APSK 4/5 Short'
			    83) '16APSK 4/5 Short w/Pilot'
			    84) '16APSK 5/6 Normal'
			    85) '16APSK 5/6 Normal w/Pilot'
			    86) '16APSK 5/6 Short'
			    87) '16APSK 5/6 Short w/Pilot'
			    88) '16APSK 8/9 Normal'
			    89) '16APSK 8/9 Normal w/Pilot'
			    90) '16APSK 8/9 Short'
			    91) '16APSK 8/9 Short w/Pilot'
			    92) '16APSK 9/10 Normal'
			    93) '16APSK 9/10 Normal w/Pilot'
			    96) '32APSK 3/4 Normal'
			    97) '32APSK 3/4 Normal w/Pilot'
			    98) '32APSK 3/4 Short'
			    99) '32APSK 3/4 Short w/Pilot'
			    100) '32APSK 4/5 Normal'
			    101) '32APSK 4/5 Normal w/Pilot'
			    102) '32APSK 4/5 Short'
			    103) '32APSK 4/5 Short w/Pilot'
			    104) '32APSK 5/6 Normal'
			    105) '32APSK 5/6 Normal w/Pilot'
			    106) '32APSK 5/6 Short'
			    107) '32APSK 5/6 Short w/Pilot'
			    108) '32APSK 8/9 Normal'
			    109) '32APSK 8/9 Normal w/Pilot'
			    110) '32APSK 8/9 Short'
			    111) '32APSK 8/9 Short w/Pilot'
			    112) '32APSK 9/10 Normal'
			    113) '32APSK 9/10 Normal w/Pilot'
			    132) 'QPSK 13/45 Normal'
			    133) 'QPSK 13/45 Normal w/Pilot'
			    134) 'QPSK 9/20 Normal'
			    135) 'QPSK 9/20 Normal w/Pilot'
			    136) 'QPSK 11/20 Normal'
			    137) 'QPSK 11/20 Normal w/Pilot'
			    138) '8APSK 5/9-L Normal'
			    139) '8APSK 5/9-L Normal w/Pilot'
			    140) '8APSK 26/45-L Normal'
			    141) '8APSK 26/45-L Normal w/Pilot'
			    142) '8PSK 23/36 Normal'
			    143) '8PSK 23/36 Normal w/Pilot'
			    144) '8PSK 25/36 Normal'
			    145) '8PSK 25/36 Normal w/Pilot'
			    146) '8PSK 13/18 Normal'
			    147) '8PSK 13/18 Normal w/Pilot'
			    148) '16APSK 1/2-L Normal'
			    149) '16APSK 1/2-L Normal w/Pilot'
			    150) '16APSK 8/15-L Normal'
			    151) '16APSK 8/15-L Normal w/Pilot'
			    152) '16APSK 5/9-L Normal'
			    153) '16APSK 5/9-L Normal w/Pilot'
			    154) '16APSK 26/45 Normal'
			    155) '16APSK 26/45 Normal w/Pilot'
			    156) '16APSK 3/5 Normal'
			    157) '16APSK 3/5 Normal w/Pilot'
			    158) '16APSK 3/5-L Normal'
			    159) '16APSK 3/5-L Normal w/Pilot'
			    160) '16APSK 28/45 Normal'
			    161) '16APSK 28/45 Normal w/Pilot'
			    162) '16APSK 23/36 Normal'
			    163) '16APSK 23/36 Normal w/Pilot'
			    164) '16APSK 2/3-L Normal'
			    165) '16APSK 2/3-L Normal w/Pilot'
			    166) '16APSK 25/36 Normal'
			    167) '16APSK 25/36 Normal w/Pilot'
			    168) '16APSK 13/18 Normal'
			    169) '16APSK 13/18 Normal w/Pilot'
			    170) '16APSK 7/9 Normal'
			    171) '16APSK 7/9 Normal w/Pilot'
			    172) '16APSK 77/90 Normal'
			    173) '16APSK 77/90 Normal w/Pilot'
			    174) '32APSK 2/3-L Normal'
			    175) '32APSK 2/3-L Normal w/Pilot'
			    178) '32APSK 32/45 Normal'
			    179) '32APSK 32/45 Normal w/Pilot'
			    180) '32APSK 11/15 Normal'
			    181) '32APSK 11/15 Normal w/Pilot'
			    182) '32APSK 7/9 Normal'
			    183) '32APSK 7/9 Normal w/Pilot'
			    184) '64APSK 32/45-L Normal'
			    185) '64APSK 32/45-L Normal w/Pilot'
			    186) '64APSK 11/15 Normal'
			    187) '64APSK 11/15 Normal w/Pilot'
			    190) '64APSK 7/9 Normal'
			    191) '64APSK 7/9 Normal w/Pilot'
			    194) '64APSK 4/5 Normal'
			    195) '64APSK 4/5 Normal w/Pilot'
			    198) '64APSK 5/6 Normal'
			    199) '64APSK 5/6 Normal w/Pilot'
			    200) '128APSK 3/4 Normal'
			    201) '128APSK 3/4 Normal w/Pilot'
			    202) '128APSK 7/9 Normal'
			    203) '128APSK 7/9 Normal w/Pilot'
			    204) '256APSK 29/45-L Normal'
			    205) '256APSK 29/45-L Normal w/Pilot'
			    206) '256APSK 2/3-L Normal'
			    207) '256APSK 2/3-L Normal w/Pilot'
			    208) '256APSK 31/45-L Normal'
			    209) '256APSK 31/45-L Normal w/Pilot'
			    210) '256APSK 32/45 Normal'
			    211) '256APSK 32/45 Normal w/Pilot'
			    212) '256APSK 11/15-L Normal'
			    213) '256APSK 11/15-L Normal w/Pilot'
			    214) '256APSK 3/4 Normal'
			    215) '256APSK 3/4 Normal w/Pilot'
			    216) 'QPSK 11/45 Short'
			    217) 'QPSK 11/45 Short w/Pilot'
			    218) 'QPSK 4/15 Short'
			    219) 'QPSK 4/15 Short w/Pilot'
			    220) 'QPSK 14/45 Short'
			    221) 'QPSK 14/45 Short w/Pilot'
			    222) 'QPSK 7/15 Short'
			    223) 'QPSK 7/15 Short w/Pilot'
			    224) 'QPSK 8/15 Short'
			    225) 'QPSK 8/15 Short w/Pilot'
			    226) 'QPSK 32/45 Short'
			    227) 'QPSK 32/45 Short w/Pilot'
			    228) '8PSK 7/15 Short'
			    229) '8PSK 7/15 Short w/Pilot'
			    230) '8PSK 8/15 Short'
			    231) '8PSK 8/15 Short w/Pilot'
			    232) '8PSK 26/45 Short'
			    233) '8PSK 26/45 Short w/Pilot'
			    234) '8PSK 32/45 Short'
			    235) '8PSK 32/45 Short w/Pilot'
			    236) '16APSK 7/15 Short'
			    237) '16APSK 7/15 Short w/Pilot'
			    238) '16APSK 8/15 Short'
			    239) '16APSK 8/15 Short w/Pilot'
			    240) '16APSK 26/45 Short'
			    241) '16APSK 26/45 Short w/Pilot'
			    242) '16APSK 3/5 Short'
			    243) '16APSK 3/5 Short w/Pilot'
			    244) '16APSK 32/45 Short'
			    245) '16APSK 32/45 Short w/Pilot'
			    246) '32APSK 2/3 Short'
			    247) '32APSK 2/3 Short w/Pilot'
			    248) '32APSK 32/45 Short'
			    249) '32APSK 32/45 Short w/Pilot'
			    256) 'Unlocked'
			Oid=1.3.6.1.4.1.31968.3.1.4.2.2.2.18
			"
	::= { rxNotifObjects 18 }

rxModcodLdpcGen2Info OBJECT-TYPE
	SYNTAX		INTEGER {
		bpsk12(0),
		bpsk815(1),
		bpsk47(2),
		bpsk813(3),
		bpsk23(4),
		bpsk1623(5),
		bpsk811(6),
		qpsk12(7),
		qpsk815(8),
		qpsk47(9),
		qpsk813(10),
		qpsk23(11),
		qpsk1623(12),
		qpsk811(13),
		qpsk1621(14),
		qpsk45(15),
		qpsk1619(16),
		qpsk89(17),
		n8psk813(18),
		n8psk23(19),
		n8psk1623(20),
		n8apsk813(21),
		n8apsk23(22),
		n8apsk1623(23),
		n16apsk47(24),
		n16apsk813(25),
		n16apsk23(26),
		n16apsk1623(27),
		n16apsk811(28),
		n16apsk1621(29),
		n16apsk45(30),
		n16apsk1619(31),
		n16apsk89(32),
		n16apsk1617(33),
		n16qam12(34),
		n16qam815(35),
		n16qam47(36),
		n16qam813(37),
		n16qam23(38),
		n16qam1623(39),
		n16qam811(40),
		n16qam1621(41),
		n16qam45(42),
		n16qam1619(43),
		n16qam89(44),
		n16qam1617(45),
		n32qam23(46),
		n32qam1623(47),
		n32qam811(48),
		n32qam1621(49),
		n32qam45(50),
		n32qam1619(51),
		n32qam89(52),
		n32qam1617(53),
		n64qam23(54),
		n64qam1623(55),
		n64qam811(56),
		n64qam1621(57),
		n64qam45(58),
		n64qam1619(59),
		n64qam89(60),
		n64qam1617(61),
		idle(62),
		unlocked(128)
	}
	MAX-ACCESS	accessible-for-notify
	STATUS		current
	DESCRIPTION "Rx LDPC-Gen2 ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'QPSK 1/2'
			    8) 'QPSK 8/15'
			    9) 'QPSK 4/7'
			    10) 'QPSK 8/13'
			    11) 'QPSK 2/3'
			    12) 'QPSK 16/23'
			    13) 'QPSK 8/11'
			    14) 'QPSK 16/21'
			    15) 'QPSK 4/5'
			    16) 'QPSK 16/19'
			    17) 'QPSK 8/9'
			    18) '8PSK 8/13'
			    19) '8PSK 2/3'
			    20) '8PSK 16/23'
			    21) '8APSK 8/13'
			    22) '8APSK 2/3'
			    23) '8APSK 16/23'
			    24) '16APSK 4/7'
			    25) '16APSK 8/13'
			    26) '16APSK 2/3'
			    27) '16APSK 16/23'
			    28) '16APSK 8/11'
			    29) '16APSK 16/21'
			    30) '16APSK 4/5'
			    31) '16APSK 16/19'
			    32) '16APSK 8/9'
			    33) '16APSK 16/17'
			    34) '16QAM 1/2'
			    35) '16QAM 8/15'
			    36) '16QAM 4/7'
			    37) '16QAM 8/13'
			    38) '16QAM 2/3'
			    39) '16QAM 16/23'
			    40) '16QAM 8/11'
			    41) '16QAM 16/21'
			    42) '16QAM 4/5'
			    43) '16QAM 16/19'
			    44) '16QAM 8/9'
			    45) '16QAM 16/17'
			    46) '32QAM 2/3'
			    47) '32QAM 16/23'
			    48) '32QAM 8/11'
			    49) '32QAM 16/21'
			    50) '32QAM 4/5'
			    51) '32QAM 16/19'
			    52) '32QAM 8/9'
			    53) '32QAM 16/17'
			    54) '64QAM 2/3'
			    55) '64QAM 16/23'
			    56) '64QAM 8/11'
			    57) '64QAM 16/21'
			    58) '64QAM 4/5'
			    59) '64QAM 16/19'
			    60) '64QAM 8/9'
			    61) '64QAM 16/17'
			    62) 'Idle'
			    128) 'Unlocked'
			Oid=1.3.6.1.4.1.31968.3.1.4.2.2.2.19
			"
	::= { rxNotifObjects 19 }

rxModcodLdpcGen2BlockSizeInfo OBJECT-TYPE
	SYNTAX		INTEGER {
		n2kBlock(0),
		n4kBlock(1),
		n8kBlock(2),
		n16kBlock(3)
	}
	MAX-ACCESS	accessible-for-notify
	STATUS		current
	DESCRIPTION "Rx LDPC-Gen2 ModCod Block Size, where:
			    0) '2k Block'
			    1) '4k Block'
			    2) '8k Block'
			    3) '16k Block'
			Oid=1.3.6.1.4.1.31968.3.1.4.2.2.2.20
			"
	::= { rxNotifObjects 20 }

rxAcmLowAlarmInfo OBJECT-TYPE
	SYNTAX		INTEGER {
		acmEsN0Ok(0),
		acmLowEsN0Alarm(1)
	}
	MAX-ACCESS	accessible-for-notify
	STATUS		current
	DESCRIPTION "Rx ACM Low Es/N0 Alarm, where:
			    0) 'ACM Es/N0 Ok'
			    1) 'ACM LOW Es/N0 ALARM'
			Oid=1.3.6.1.4.1.31968.3.1.4.2.2.2.21
			"
	::= { rxNotifObjects 21 }

rxAcmLowEsn0Info OBJECT-TYPE
	SYNTAX		Integer32
	UNITS		"0.01 dB"
	MAX-ACCESS	accessible-for-notify
	STATUS		current
	DESCRIPTION "Rx ACM EsN0
			Oid=1.3.6.1.4.1.31968.3.1.4.2.2.2.22
			"
	::= { rxNotifObjects 22 }

rxDataAlarmInfo OBJECT-TYPE
	SYNTAX		INTEGER {
		dataOk(0),
		dataInactivityAlarm(1)
	}
	MAX-ACCESS	accessible-for-notify
	STATUS		current
	DESCRIPTION "Rx Data Activity Alarm, where:
			    0) 'Data Ok'
			    1) 'DATA INACTIVITY ALARM'
			Oid=1.3.6.1.4.1.31968.3.1.4.2.2.2.23
			"
	::= { rxNotifObjects 23 }

rxDataConfigurationMismatchInfo OBJECT-TYPE
	SYNTAX		INTEGER {
		rxTxDataConfigurationOk(0),
		rxTxDataConfigurationMismatched(1)
	}
	MAX-ACCESS	accessible-for-notify
	STATUS		current
	DESCRIPTION "Rx Rx/Tx Configuration Mismatch, where:
			    0) 'Rx/Tx Data Configuration Ok'
			    1) 'Rx/Tx DATA CONFIGURATION MISMATCHED'
			Oid=1.3.6.1.4.1.31968.3.1.4.2.2.2.24
			"
	::= { rxNotifObjects 24 }

rxTemperatureAlarmInfo OBJECT-TYPE
	SYNTAX		INTEGER {
		temperatureOk(0),
		overTemperatureAlarm(1)
	}
	MAX-ACCESS	accessible-for-notify
	STATUS		current
	DESCRIPTION "Rx Temperature Alarm, where:
			    0) 'Temperature Ok'
			    1) 'OVER TEMPERATURE ALARM'
			Oid=1.3.6.1.4.1.31968.3.1.4.2.2.2.25
			"
	::= { rxNotifObjects 25 }

rxRfTemperatureInfo OBJECT-TYPE
	SYNTAX		Integer32
	UNITS		"0.1 Degree C"
	MAX-ACCESS	accessible-for-notify
	STATUS		current
	DESCRIPTION "Rx RF Temperature
			Oid=1.3.6.1.4.1.31968.3.1.4.2.2.2.26
			"
	::= { rxNotifObjects 26 }

rxFpga2TemperatureInfo OBJECT-TYPE
	SYNTAX		Integer32
	UNITS		"0.1 Degree C"
	MAX-ACCESS	accessible-for-notify
	STATUS		current
	DESCRIPTION "Rx FPGA 2 Temperature
			Oid=1.3.6.1.4.1.31968.3.1.4.2.2.2.27
			"
	::= { rxNotifObjects 27 }

rxFpga3TemperatureInfo OBJECT-TYPE
	SYNTAX		Integer32
	UNITS		"0.1 Degree C"
	MAX-ACCESS	accessible-for-notify
	STATUS		current
	DESCRIPTION "Rx FPGA 3 Temperature
			Oid=1.3.6.1.4.1.31968.3.1.4.2.2.2.28
			"
	::= { rxNotifObjects 28 }

rxHardwareAlarmInfo OBJECT-TYPE
	SYNTAX		INTEGER {
		hardwareAlarmOk(0),
		hardwareAlarm(1)
	}
	MAX-ACCESS	accessible-for-notify
	STATUS		current
	DESCRIPTION "Rx Hardware Alarm, where:
			    0) 'Hardware Alarm Ok'
			    1) 'HARDWARE ALARM'
			Oid=1.3.6.1.4.1.31968.3.1.4.2.2.2.29
			"
	::= { rxNotifObjects 29 }

rxHardwareAlarmBitsInfo OBJECT-TYPE
	SYNTAX		BITS {
		vint2(0),
		vaux2(1),
		clock2(2),
		n100mhz(3),
		lo(4),
		memory2(5),
		invalidKey(6),
		vint3(7),
		vaux3(8),
		clock3(9),
		memory3(10),
		temperature(11)
	}
	MAX-ACCESS	accessible-for-notify
	STATUS		current
	DESCRIPTION "Rx Binary Hardware Alarms, where:
			    0) 'VInt2'
			    1) 'VAux2'
			    2) 'Clock2'
			    3) '100MHz'
			    4) 'LO'
			    5) 'Memory2'
			    6) 'Invalid Key'
			    7) 'VInt3'
			    8) 'VAux3'
			    9) 'Clock3'
			    10) 'Memory3'
			    11) 'Temperature'
			Oid=1.3.6.1.4.1.31968.3.1.4.2.2.2.30
			"
	::= { rxNotifObjects 30 }

rxDataPortLinkRateAlarmInfo OBJECT-TYPE
	SYNTAX		INTEGER {
		linkRateOk(0),
		linkRateAlarm(1)
	}
	MAX-ACCESS	accessible-for-notify
	STATUS		current
	DESCRIPTION "Rx Data Port Link Rate Alarm, where:
			    0) 'Link Rate Ok'
			    1) 'LINK RATE ALARM'
			Oid=1.3.6.1.4.1.31968.3.1.4.2.2.2.31
			"
	::= { rxNotifObjects 31 }

rxAcmTxHubAlarmInfo OBJECT-TYPE
	SYNTAX		INTEGER {
		acmTxHubMessageOk(0),
		acmTxHubMessageAlarm(1)
	}
	MAX-ACCESS	accessible-for-notify
	STATUS		current
	DESCRIPTION "Rx ACM Tx Hub Alarm, where:
			    0) 'ACM Tx Hub Message Ok'
			    1) 'ACM Tx HUB MESSAGE ALARM'
			Oid=1.3.6.1.4.1.31968.3.1.4.2.2.2.32
			"
	::= { rxNotifObjects 32 }

txChannelInfo OBJECT-TYPE
	SYNTAX		Unsigned32
	UNITS		"1"
	MAX-ACCESS	accessible-for-notify
	STATUS		current
	DESCRIPTION "Tx Channel Number
			Oid=1.3.6.1.4.1.31968.3.1.4.2.2.3.1
			"
	::= { txNotifObjects 1 }

txWaveformInfo OBJECT-TYPE
	SYNTAX		INTEGER {
		off(0),
		dvbS2x(1),
		mil165bDvbS2x(2),
		dvbS2xVcm(3),
		dvbS2xIqoe(4),
		ldpcGen2(5),
		ldpcGen2Dsss(6),
		segmentedLdpcGen2(7),
		shutdown(8),
		calibration(9),
		fipsValidate(10)
	}
	MAX-ACCESS	accessible-for-notify
	STATUS		current
	DESCRIPTION "Tx Waveform, where:
			    0) 'Off'
			    1) 'DVB-S2X'
			    2) 'MIL 165B DVB-S2X'
			    3) 'DVB-S2X VCM'
			    4) 'DVB-S2X IQoE'
			    5) 'LDPC-Gen2'
			    6) 'LDPC-Gen2 DSSS'
			    7) 'Segmented LDPC-Gen2'
			    8) 'SHUTDOWN'
			    9) 'Calibration'
			    10) 'FIPS Validate'
			Oid=1.3.6.1.4.1.31968.3.1.4.2.2.3.2
			"
	::= { txNotifObjects 2 }

txRfCxrInfo OBJECT-TYPE
	SYNTAX		INTEGER {
		off(0),
		on(1)
	}
	MAX-ACCESS	accessible-for-notify
	STATUS		current
	DESCRIPTION "Tx RF Master Output, where:
			    0) 'Off'
			    1) 'On'
			Oid=1.3.6.1.4.1.31968.3.1.4.2.2.3.3
			"
	::= { txNotifObjects 3 }

txOutputInfo OBJECT-TYPE
	SYNTAX		INTEGER {
		off(0),
		on(1),
		onDataIdle(2),
		onDataLive(3),
		onDataDown(4),
		onDataPendingToGoDown(5),
		onDataPendingToGoUp(6),
		onDataUp(7),
		allPendingToCurrentAndNotifyRx(8)
	}
	MAX-ACCESS	accessible-for-notify
	STATUS		current
	DESCRIPTION "Tx Output, where:
			    0) 'Off'
			    1) 'On'
			    2) 'On, Data Idle'
			    3) 'On, Data Live'
			    4) 'On, Data Down'
			    5) 'On, Data Pending To Go Down'
			    6) 'On, Data Pending To Go Up'
			    7) 'On, Data Up'
			    8) 'All Pending To Current & Notify Rx'
			Oid=1.3.6.1.4.1.31968.3.1.4.2.2.3.4
			"
	::= { txNotifObjects 4 }

txCxrMuteInfo OBJECT-TYPE
	SYNTAX		INTEGER {
		carrierOk(0),
		cxrMuted(1)
	}
	MAX-ACCESS	accessible-for-notify
	STATUS		current
	DESCRIPTION "Tx Carrier Mute, where:
			    0) 'Carrier Ok'
			    1) 'CXR MUTED'
			Oid=1.3.6.1.4.1.31968.3.1.4.2.2.3.5
			"
	::= { txNotifObjects 5 }

txAupcAlarmInfo OBJECT-TYPE
	SYNTAX		INTEGER {
		aupcOk(0),
		aupcAlarm(1)
	}
	MAX-ACCESS	accessible-for-notify
	STATUS		current
	DESCRIPTION "Tx AUPC Alarm, where:
			    0) 'AUPC Ok'
			    1) 'AUPC ALARM'
			Oid=1.3.6.1.4.1.31968.3.1.4.2.2.3.6
			"
	::= { txNotifObjects 6 }

txRemoteChannelAlarmInfo OBJECT-TYPE
	SYNTAX		INTEGER {
		remoteChannleOk(0),
		remoteChannelAlarm(1)
	}
	MAX-ACCESS	accessible-for-notify
	STATUS		current
	DESCRIPTION "Tx Remote Channel Alarm, where:
			    0) 'Remote Channle Ok'
			    1) 'REMOTE CHANNEL ALARM'
			Oid=1.3.6.1.4.1.31968.3.1.4.2.2.3.7
			"
	::= { txNotifObjects 7 }

txTransecInfo OBJECT-TYPE
	SYNTAX		INTEGER {
		notInstalled(0),
		temperatureAlarm(1),
		hardwareAlarm(2),
		selfTestFailure(3),
		notOperational(4),
		coIdentifierKeysZeroizedLog(5),
		keyNotInitializedLog(6),
		dataNotEncryptedLog(7),
		errorKeyIndexExpiredLog(8),
		dataEncryptedLog(9),
		coIdentifierKeysZeroized(10),
		keyNotInitialized(11),
		dataNotEncrypted(12),
		errorKeyIndexExpired(13),
		dataEncrypted(14),
		alarmNotInstalled(15),
		alarmTemperatureAlarm(16),
		alarmHardwareAlarm(17),
		alarmSelfTestFailure(18),
		alarmNotOperational(19),
		alarmCoIdentifierKeysZeroizedLog(20),
		alarmKeyNotInitializedLog(21),
		alarmDataNotEncryptedLog(22),
		alarmErrorKeyIndexExpiredLog(23),
		alarmDataEncryptedLog(24),
		alarmCoIdentifierKeysZeroized(25),
		alarmKeyNotInitialized(26),
		alarmDataNotEncrypted(27),
		alarmErrorKeyIndexExpired(28),
		alarmDataEncrypted(29)
	}
	MAX-ACCESS	accessible-for-notify
	STATUS		current
	DESCRIPTION "Tx TRANSEC, where:
			    0) 'Not Installed'
			    1) 'TEMPERATURE ALARM'
			    2) 'HARDWARE ALARM'
			    3) 'SELF TEST FAILURE'
			    4) 'NOT OPERATIONAL'
			    5) 'CO Identifier/Keys Zeroized, Log'
			    6) 'KEY NOT INITIALIZED, Log'
			    7) 'DATA NOT ENCRYPTED, Log'
			    8) 'ERROR, KEY INDEX EXPIRED, Log'
			    9) 'Data Encrypted, Log'
			    10) 'CO Identifier/Keys Zeroized'
			    11) 'KEY NOT INITIALIZED'
			    12) 'DATA NOT ENCRYPTED'
			    13) 'ERROR, KEY INDEX EXPIRED'
			    14) 'Data Encrypted'
			    15) 'ALARM: Not Installed'
			    16) 'ALARM: TEMPERATURE ALARM'
			    17) 'ALARM: HARDWARE ALARM'
			    18) 'ALARM: SELF TEST FAILURE'
			    19) 'ALARM: NOT OPERATIONAL'
			    20) 'ALARM: CO Identifier/Keys Zeroized, Log'
			    21) 'ALARM: KEY NOT INITIALIZED, Log'
			    22) 'ALARM: DATA NOT ENCRYPTED, Log'
			    23) 'ALARM: ERROR, KEY INDEX EXPIRED, Log'
			    24) 'ALARM: Data Encrypted, Log'
			    25) 'ALARM: CO Identifier/Keys Zeroized'
			    26) 'ALARM: KEY NOT INITIALIZED'
			    27) 'ALARM: DATA NOT ENCRYPTED'
			    28) 'ALARM: ERROR, KEY INDEX EXPIRED'
			    29) 'ALARM: Data Encrypted'
			Oid=1.3.6.1.4.1.31968.3.1.4.2.2.3.8
			"
	::= { txNotifObjects 8 }

txModcodDvbInfo OBJECT-TYPE
	SYNTAX		INTEGER {
		qpsk14Normal(4),
		qpsk14NormalWPilot(5),
		qpsk14Short(6),
		qpsk14ShortWPilot(7),
		qpsk13Normal(8),
		qpsk13NormalWPilot(9),
		qpsk13Short(10),
		qpsk13ShortWPilot(11),
		qpsk25Normal(12),
		qpsk25NormalWPilot(13),
		qpsk25Short(14),
		qpsk25ShortWPilot(15),
		qpsk12Normal(16),
		qpsk12NormalWPilot(17),
		qpsk12Short(18),
		qpsk12ShortWPilot(19),
		qpsk35Normal(20),
		qpsk35NormalWPilot(21),
		qpsk35Short(22),
		qpsk35ShortWPilot(23),
		qpsk23Normal(24),
		qpsk23NormalWPilot(25),
		qpsk23Short(26),
		qpsk23ShortWPilot(27),
		qpsk34Normal(28),
		qpsk34NormalWPilot(29),
		qpsk34Short(30),
		qpsk34ShortWPilot(31),
		qpsk45Normal(32),
		qpsk45NormalWPilot(33),
		qpsk45Short(34),
		qpsk45ShortWPilot(35),
		qpsk56Normal(36),
		qpsk56NormalWPilot(37),
		qpsk56Short(38),
		qpsk56ShortWPilot(39),
		qpsk89Normal(40),
		qpsk89NormalWPilot(41),
		qpsk89Short(42),
		qpsk89ShortWPilot(43),
		qpsk910Normal(44),
		qpsk910NormalWPilot(45),
		n8psk35Normal(48),
		n8psk35NormalWPilot(49),
		n8psk35Short(50),
		n8psk35ShortWPilot(51),
		n8psk23Normal(52),
		n8psk23NormalWPilot(53),
		n8psk23Short(54),
		n8psk23ShortWPilot(55),
		n8psk34Normal(56),
		n8psk34NormalWPilot(57),
		n8psk34Short(58),
		n8psk34ShortWPilot(59),
		n8psk56Normal(60),
		n8psk56NormalWPilot(61),
		n8psk56Short(62),
		n8psk56ShortWPilot(63),
		n8psk89Normal(64),
		n8psk89NormalWPilot(65),
		n8psk89Short(66),
		n8psk89ShortWPilot(67),
		n8psk910Normal(68),
		n8psk910NormalWPilot(69),
		n16apsk23Normal(72),
		n16apsk23NormalWPilot(73),
		n16apsk23Short(74),
		n16apsk23ShortWPilot(75),
		n16apsk34Normal(76),
		n16apsk34NormalWPilot(77),
		n16apsk34Short(78),
		n16apsk34ShortWPilot(79),
		n16apsk45Normal(80),
		n16apsk45NormalWPilot(81),
		n16apsk45Short(82),
		n16apsk45ShortWPilot(83),
		n16apsk56Normal(84),
		n16apsk56NormalWPilot(85),
		n16apsk56Short(86),
		n16apsk56ShortWPilot(87),
		n16apsk89Normal(88),
		n16apsk89NormalWPilot(89),
		n16apsk89Short(90),
		n16apsk89ShortWPilot(91),
		n16apsk910Normal(92),
		n16apsk910NormalWPilot(93),
		n32apsk34Normal(96),
		n32apsk34NormalWPilot(97),
		n32apsk34Short(98),
		n32apsk34ShortWPilot(99),
		n32apsk45Normal(100),
		n32apsk45NormalWPilot(101),
		n32apsk45Short(102),
		n32apsk45ShortWPilot(103),
		n32apsk56Normal(104),
		n32apsk56NormalWPilot(105),
		n32apsk56Short(106),
		n32apsk56ShortWPilot(107),
		n32apsk89Normal(108),
		n32apsk89NormalWPilot(109),
		n32apsk89Short(110),
		n32apsk89ShortWPilot(111),
		n32apsk910Normal(112),
		n32apsk910NormalWPilot(113),
		qpsk1345Normal(132),
		qpsk1345NormalWPilot(133),
		qpsk920Normal(134),
		qpsk920NormalWPilot(135),
		qpsk1120Normal(136),
		qpsk1120NormalWPilot(137),
		n8apsk59LNormal(138),
		n8apsk59LNormalWPilot(139),
		n8apsk2645LNormal(140),
		n8apsk2645LNormalWPilot(141),
		n8psk2336Normal(142),
		n8psk2336NormalWPilot(143),
		n8psk2536Normal(144),
		n8psk2536NormalWPilot(145),
		n8psk1318Normal(146),
		n8psk1318NormalWPilot(147),
		n16apsk12LNormal(148),
		n16apsk12LNormalWPilot(149),
		n16apsk815LNormal(150),
		n16apsk815LNormalWPilot(151),
		n16apsk59LNormal(152),
		n16apsk59LNormalWPilot(153),
		n16apsk2645Normal(154),
		n16apsk2645NormalWPilot(155),
		n16apsk35Normal(156),
		n16apsk35NormalWPilot(157),
		n16apsk35LNormal(158),
		n16apsk35LNormalWPilot(159),
		n16apsk2845Normal(160),
		n16apsk2845NormalWPilot(161),
		n16apsk2336Normal(162),
		n16apsk2336NormalWPilot(163),
		n16apsk23LNormal(164),
		n16apsk23LNormalWPilot(165),
		n16apsk2536Normal(166),
		n16apsk2536NormalWPilot(167),
		n16apsk1318Normal(168),
		n16apsk1318NormalWPilot(169),
		n16apsk79Normal(170),
		n16apsk79NormalWPilot(171),
		n16apsk7790Normal(172),
		n16apsk7790NormalWPilot(173),
		n32apsk23LNormal(174),
		n32apsk23LNormalWPilot(175),
		n32apsk3245Normal(178),
		n32apsk3245NormalWPilot(179),
		n32apsk1115Normal(180),
		n32apsk1115NormalWPilot(181),
		n32apsk79Normal(182),
		n32apsk79NormalWPilot(183),
		n64apsk3245LNormal(184),
		n64apsk3245LNormalWPilot(185),
		n64apsk1115Normal(186),
		n64apsk1115NormalWPilot(187),
		n64apsk79Normal(190),
		n64apsk79NormalWPilot(191),
		n64apsk45Normal(194),
		n64apsk45NormalWPilot(195),
		n64apsk56Normal(198),
		n64apsk56NormalWPilot(199),
		n128apsk34Normal(200),
		n128apsk34NormalWPilot(201),
		n128apsk79Normal(202),
		n128apsk79NormalWPilot(203),
		n256apsk2945LNormal(204),
		n256apsk2945LNormalWPilot(205),
		n256apsk23LNormal(206),
		n256apsk23LNormalWPilot(207),
		n256apsk3145LNormal(208),
		n256apsk3145LNormalWPilot(209),
		n256apsk3245Normal(210),
		n256apsk3245NormalWPilot(211),
		n256apsk1115LNormal(212),
		n256apsk1115LNormalWPilot(213),
		n256apsk34Normal(214),
		n256apsk34NormalWPilot(215),
		qpsk1145Short(216),
		qpsk1145ShortWPilot(217),
		qpsk415Short(218),
		qpsk415ShortWPilot(219),
		qpsk1445Short(220),
		qpsk1445ShortWPilot(221),
		qpsk715Short(222),
		qpsk715ShortWPilot(223),
		qpsk815Short(224),
		qpsk815ShortWPilot(225),
		qpsk3245Short(226),
		qpsk3245ShortWPilot(227),
		n8psk715Short(228),
		n8psk715ShortWPilot(229),
		n8psk815Short(230),
		n8psk815ShortWPilot(231),
		n8psk2645Short(232),
		n8psk2645ShortWPilot(233),
		n8psk3245Short(234),
		n8psk3245ShortWPilot(235),
		n16apsk715Short(236),
		n16apsk715ShortWPilot(237),
		n16apsk815Short(238),
		n16apsk815ShortWPilot(239),
		n16apsk2645Short(240),
		n16apsk2645ShortWPilot(241),
		n16apsk35Short(242),
		n16apsk35ShortWPilot(243),
		n16apsk3245Short(244),
		n16apsk3245ShortWPilot(245),
		n32apsk23Short(246),
		n32apsk23ShortWPilot(247),
		n32apsk3245Short(248),
		n32apsk3245ShortWPilot(249),
		unlocked(256)
	}
	MAX-ACCESS	accessible-for-notify
	STATUS		current
	DESCRIPTION "Tx DVB-S2X ModCod, where:
			    4) 'QPSK 1/4 Normal'
			    5) 'QPSK 1/4 Normal w/Pilot'
			    6) 'QPSK 1/4 Short'
			    7) 'QPSK 1/4 Short w/Pilot'
			    8) 'QPSK 1/3 Normal'
			    9) 'QPSK 1/3 Normal w/Pilot'
			    10) 'QPSK 1/3 Short'
			    11) 'QPSK 1/3 Short w/Pilot'
			    12) 'QPSK 2/5 Normal'
			    13) 'QPSK 2/5 Normal w/Pilot'
			    14) 'QPSK 2/5 Short'
			    15) 'QPSK 2/5 Short w/Pilot'
			    16) 'QPSK 1/2 Normal'
			    17) 'QPSK 1/2 Normal w/Pilot'
			    18) 'QPSK 1/2 Short'
			    19) 'QPSK 1/2 Short w/Pilot'
			    20) 'QPSK 3/5 Normal'
			    21) 'QPSK 3/5 Normal w/Pilot'
			    22) 'QPSK 3/5 Short'
			    23) 'QPSK 3/5 Short w/Pilot'
			    24) 'QPSK 2/3 Normal'
			    25) 'QPSK 2/3 Normal w/Pilot'
			    26) 'QPSK 2/3 Short'
			    27) 'QPSK 2/3 Short w/Pilot'
			    28) 'QPSK 3/4 Normal'
			    29) 'QPSK 3/4 Normal w/Pilot'
			    30) 'QPSK 3/4 Short'
			    31) 'QPSK 3/4 Short w/Pilot'
			    32) 'QPSK 4/5 Normal'
			    33) 'QPSK 4/5 Normal w/Pilot'
			    34) 'QPSK 4/5 Short'
			    35) 'QPSK 4/5 Short w/Pilot'
			    36) 'QPSK 5/6 Normal'
			    37) 'QPSK 5/6 Normal w/Pilot'
			    38) 'QPSK 5/6 Short'
			    39) 'QPSK 5/6 Short w/Pilot'
			    40) 'QPSK 8/9 Normal'
			    41) 'QPSK 8/9 Normal w/Pilot'
			    42) 'QPSK 8/9 Short'
			    43) 'QPSK 8/9 Short w/Pilot'
			    44) 'QPSK 9/10 Normal'
			    45) 'QPSK 9/10 Normal w/Pilot'
			    48) '8PSK 3/5 Normal'
			    49) '8PSK 3/5 Normal w/Pilot'
			    50) '8PSK 3/5 Short'
			    51) '8PSK 3/5 Short w/Pilot'
			    52) '8PSK 2/3 Normal'
			    53) '8PSK 2/3 Normal w/Pilot'
			    54) '8PSK 2/3 Short'
			    55) '8PSK 2/3 Short w/Pilot'
			    56) '8PSK 3/4 Normal'
			    57) '8PSK 3/4 Normal w/Pilot'
			    58) '8PSK 3/4 Short'
			    59) '8PSK 3/4 Short w/Pilot'
			    60) '8PSK 5/6 Normal'
			    61) '8PSK 5/6 Normal w/Pilot'
			    62) '8PSK 5/6 Short'
			    63) '8PSK 5/6 Short w/Pilot'
			    64) '8PSK 8/9 Normal'
			    65) '8PSK 8/9 Normal w/Pilot'
			    66) '8PSK 8/9 Short'
			    67) '8PSK 8/9 Short w/Pilot'
			    68) '8PSK 9/10 Normal'
			    69) '8PSK 9/10 Normal w/Pilot'
			    72) '16APSK 2/3 Normal'
			    73) '16APSK 2/3 Normal w/Pilot'
			    74) '16APSK 2/3 Short'
			    75) '16APSK 2/3 Short w/Pilot'
			    76) '16APSK 3/4 Normal'
			    77) '16APSK 3/4 Normal w/Pilot'
			    78) '16APSK 3/4 Short'
			    79) '16APSK 3/4 Short w/Pilot'
			    80) '16APSK 4/5 Normal'
			    81) '16APSK 4/5 Normal w/Pilot'
			    82) '16APSK 4/5 Short'
			    83) '16APSK 4/5 Short w/Pilot'
			    84) '16APSK 5/6 Normal'
			    85) '16APSK 5/6 Normal w/Pilot'
			    86) '16APSK 5/6 Short'
			    87) '16APSK 5/6 Short w/Pilot'
			    88) '16APSK 8/9 Normal'
			    89) '16APSK 8/9 Normal w/Pilot'
			    90) '16APSK 8/9 Short'
			    91) '16APSK 8/9 Short w/Pilot'
			    92) '16APSK 9/10 Normal'
			    93) '16APSK 9/10 Normal w/Pilot'
			    96) '32APSK 3/4 Normal'
			    97) '32APSK 3/4 Normal w/Pilot'
			    98) '32APSK 3/4 Short'
			    99) '32APSK 3/4 Short w/Pilot'
			    100) '32APSK 4/5 Normal'
			    101) '32APSK 4/5 Normal w/Pilot'
			    102) '32APSK 4/5 Short'
			    103) '32APSK 4/5 Short w/Pilot'
			    104) '32APSK 5/6 Normal'
			    105) '32APSK 5/6 Normal w/Pilot'
			    106) '32APSK 5/6 Short'
			    107) '32APSK 5/6 Short w/Pilot'
			    108) '32APSK 8/9 Normal'
			    109) '32APSK 8/9 Normal w/Pilot'
			    110) '32APSK 8/9 Short'
			    111) '32APSK 8/9 Short w/Pilot'
			    112) '32APSK 9/10 Normal'
			    113) '32APSK 9/10 Normal w/Pilot'
			    132) 'QPSK 13/45 Normal'
			    133) 'QPSK 13/45 Normal w/Pilot'
			    134) 'QPSK 9/20 Normal'
			    135) 'QPSK 9/20 Normal w/Pilot'
			    136) 'QPSK 11/20 Normal'
			    137) 'QPSK 11/20 Normal w/Pilot'
			    138) '8APSK 5/9-L Normal'
			    139) '8APSK 5/9-L Normal w/Pilot'
			    140) '8APSK 26/45-L Normal'
			    141) '8APSK 26/45-L Normal w/Pilot'
			    142) '8PSK 23/36 Normal'
			    143) '8PSK 23/36 Normal w/Pilot'
			    144) '8PSK 25/36 Normal'
			    145) '8PSK 25/36 Normal w/Pilot'
			    146) '8PSK 13/18 Normal'
			    147) '8PSK 13/18 Normal w/Pilot'
			    148) '16APSK 1/2-L Normal'
			    149) '16APSK 1/2-L Normal w/Pilot'
			    150) '16APSK 8/15-L Normal'
			    151) '16APSK 8/15-L Normal w/Pilot'
			    152) '16APSK 5/9-L Normal'
			    153) '16APSK 5/9-L Normal w/Pilot'
			    154) '16APSK 26/45 Normal'
			    155) '16APSK 26/45 Normal w/Pilot'
			    156) '16APSK 3/5 Normal'
			    157) '16APSK 3/5 Normal w/Pilot'
			    158) '16APSK 3/5-L Normal'
			    159) '16APSK 3/5-L Normal w/Pilot'
			    160) '16APSK 28/45 Normal'
			    161) '16APSK 28/45 Normal w/Pilot'
			    162) '16APSK 23/36 Normal'
			    163) '16APSK 23/36 Normal w/Pilot'
			    164) '16APSK 2/3-L Normal'
			    165) '16APSK 2/3-L Normal w/Pilot'
			    166) '16APSK 25/36 Normal'
			    167) '16APSK 25/36 Normal w/Pilot'
			    168) '16APSK 13/18 Normal'
			    169) '16APSK 13/18 Normal w/Pilot'
			    170) '16APSK 7/9 Normal'
			    171) '16APSK 7/9 Normal w/Pilot'
			    172) '16APSK 77/90 Normal'
			    173) '16APSK 77/90 Normal w/Pilot'
			    174) '32APSK 2/3-L Normal'
			    175) '32APSK 2/3-L Normal w/Pilot'
			    178) '32APSK 32/45 Normal'
			    179) '32APSK 32/45 Normal w/Pilot'
			    180) '32APSK 11/15 Normal'
			    181) '32APSK 11/15 Normal w/Pilot'
			    182) '32APSK 7/9 Normal'
			    183) '32APSK 7/9 Normal w/Pilot'
			    184) '64APSK 32/45-L Normal'
			    185) '64APSK 32/45-L Normal w/Pilot'
			    186) '64APSK 11/15 Normal'
			    187) '64APSK 11/15 Normal w/Pilot'
			    190) '64APSK 7/9 Normal'
			    191) '64APSK 7/9 Normal w/Pilot'
			    194) '64APSK 4/5 Normal'
			    195) '64APSK 4/5 Normal w/Pilot'
			    198) '64APSK 5/6 Normal'
			    199) '64APSK 5/6 Normal w/Pilot'
			    200) '128APSK 3/4 Normal'
			    201) '128APSK 3/4 Normal w/Pilot'
			    202) '128APSK 7/9 Normal'
			    203) '128APSK 7/9 Normal w/Pilot'
			    204) '256APSK 29/45-L Normal'
			    205) '256APSK 29/45-L Normal w/Pilot'
			    206) '256APSK 2/3-L Normal'
			    207) '256APSK 2/3-L Normal w/Pilot'
			    208) '256APSK 31/45-L Normal'
			    209) '256APSK 31/45-L Normal w/Pilot'
			    210) '256APSK 32/45 Normal'
			    211) '256APSK 32/45 Normal w/Pilot'
			    212) '256APSK 11/15-L Normal'
			    213) '256APSK 11/15-L Normal w/Pilot'
			    214) '256APSK 3/4 Normal'
			    215) '256APSK 3/4 Normal w/Pilot'
			    216) 'QPSK 11/45 Short'
			    217) 'QPSK 11/45 Short w/Pilot'
			    218) 'QPSK 4/15 Short'
			    219) 'QPSK 4/15 Short w/Pilot'
			    220) 'QPSK 14/45 Short'
			    221) 'QPSK 14/45 Short w/Pilot'
			    222) 'QPSK 7/15 Short'
			    223) 'QPSK 7/15 Short w/Pilot'
			    224) 'QPSK 8/15 Short'
			    225) 'QPSK 8/15 Short w/Pilot'
			    226) 'QPSK 32/45 Short'
			    227) 'QPSK 32/45 Short w/Pilot'
			    228) '8PSK 7/15 Short'
			    229) '8PSK 7/15 Short w/Pilot'
			    230) '8PSK 8/15 Short'
			    231) '8PSK 8/15 Short w/Pilot'
			    232) '8PSK 26/45 Short'
			    233) '8PSK 26/45 Short w/Pilot'
			    234) '8PSK 32/45 Short'
			    235) '8PSK 32/45 Short w/Pilot'
			    236) '16APSK 7/15 Short'
			    237) '16APSK 7/15 Short w/Pilot'
			    238) '16APSK 8/15 Short'
			    239) '16APSK 8/15 Short w/Pilot'
			    240) '16APSK 26/45 Short'
			    241) '16APSK 26/45 Short w/Pilot'
			    242) '16APSK 3/5 Short'
			    243) '16APSK 3/5 Short w/Pilot'
			    244) '16APSK 32/45 Short'
			    245) '16APSK 32/45 Short w/Pilot'
			    246) '32APSK 2/3 Short'
			    247) '32APSK 2/3 Short w/Pilot'
			    248) '32APSK 32/45 Short'
			    249) '32APSK 32/45 Short w/Pilot'
			    256) 'Unlocked'
			Oid=1.3.6.1.4.1.31968.3.1.4.2.2.3.9
			"
	::= { txNotifObjects 9 }

txModcodLdpcGen2Info OBJECT-TYPE
	SYNTAX		INTEGER {
		bpsk12(0),
		bpsk815(1),
		bpsk47(2),
		bpsk813(3),
		bpsk23(4),
		bpsk1623(5),
		bpsk811(6),
		qpsk12(7),
		qpsk815(8),
		qpsk47(9),
		qpsk813(10),
		qpsk23(11),
		qpsk1623(12),
		qpsk811(13),
		qpsk1621(14),
		qpsk45(15),
		qpsk1619(16),
		qpsk89(17),
		n8psk813(18),
		n8psk23(19),
		n8psk1623(20),
		n8apsk813(21),
		n8apsk23(22),
		n8apsk1623(23),
		n16apsk47(24),
		n16apsk813(25),
		n16apsk23(26),
		n16apsk1623(27),
		n16apsk811(28),
		n16apsk1621(29),
		n16apsk45(30),
		n16apsk1619(31),
		n16apsk89(32),
		n16apsk1617(33),
		n16qam12(34),
		n16qam815(35),
		n16qam47(36),
		n16qam813(37),
		n16qam23(38),
		n16qam1623(39),
		n16qam811(40),
		n16qam1621(41),
		n16qam45(42),
		n16qam1619(43),
		n16qam89(44),
		n16qam1617(45),
		n32qam23(46),
		n32qam1623(47),
		n32qam811(48),
		n32qam1621(49),
		n32qam45(50),
		n32qam1619(51),
		n32qam89(52),
		n32qam1617(53),
		n64qam23(54),
		n64qam1623(55),
		n64qam811(56),
		n64qam1621(57),
		n64qam45(58),
		n64qam1619(59),
		n64qam89(60),
		n64qam1617(61),
		idle(62),
		unlocked(128)
	}
	MAX-ACCESS	accessible-for-notify
	STATUS		current
	DESCRIPTION "Tx LDPC-Gen2 ModCod, where:
			    0) 'BPSK 1/2'
			    1) 'BPSK 8/15'
			    2) 'BPSK 4/7'
			    3) 'BPSK 8/13'
			    4) 'BPSK 2/3'
			    5) 'BPSK 16/23'
			    6) 'BPSK 8/11'
			    7) 'QPSK 1/2'
			    8) 'QPSK 8/15'
			    9) 'QPSK 4/7'
			    10) 'QPSK 8/13'
			    11) 'QPSK 2/3'
			    12) 'QPSK 16/23'
			    13) 'QPSK 8/11'
			    14) 'QPSK 16/21'
			    15) 'QPSK 4/5'
			    16) 'QPSK 16/19'
			    17) 'QPSK 8/9'
			    18) '8PSK 8/13'
			    19) '8PSK 2/3'
			    20) '8PSK 16/23'
			    21) '8APSK 8/13'
			    22) '8APSK 2/3'
			    23) '8APSK 16/23'
			    24) '16APSK 4/7'
			    25) '16APSK 8/13'
			    26) '16APSK 2/3'
			    27) '16APSK 16/23'
			    28) '16APSK 8/11'
			    29) '16APSK 16/21'
			    30) '16APSK 4/5'
			    31) '16APSK 16/19'
			    32) '16APSK 8/9'
			    33) '16APSK 16/17'
			    34) '16QAM 1/2'
			    35) '16QAM 8/15'
			    36) '16QAM 4/7'
			    37) '16QAM 8/13'
			    38) '16QAM 2/3'
			    39) '16QAM 16/23'
			    40) '16QAM 8/11'
			    41) '16QAM 16/21'
			    42) '16QAM 4/5'
			    43) '16QAM 16/19'
			    44) '16QAM 8/9'
			    45) '16QAM 16/17'
			    46) '32QAM 2/3'
			    47) '32QAM 16/23'
			    48) '32QAM 8/11'
			    49) '32QAM 16/21'
			    50) '32QAM 4/5'
			    51) '32QAM 16/19'
			    52) '32QAM 8/9'
			    53) '32QAM 16/17'
			    54) '64QAM 2/3'
			    55) '64QAM 16/23'
			    56) '64QAM 8/11'
			    57) '64QAM 16/21'
			    58) '64QAM 4/5'
			    59) '64QAM 16/19'
			    60) '64QAM 8/9'
			    61) '64QAM 16/17'
			    62) 'Idle'
			    128) 'Unlocked'
			Oid=1.3.6.1.4.1.31968.3.1.4.2.2.3.10
			"
	::= { txNotifObjects 10 }

txModcodLdpcGen2BlockSizeInfo OBJECT-TYPE
	SYNTAX		INTEGER {
		n2kBlock(0),
		n4kBlock(1),
		n8kBlock(2),
		n16kBlock(3)
	}
	MAX-ACCESS	accessible-for-notify
	STATUS		current
	DESCRIPTION "Tx LDPC-Gen2 ModCod Block Size, where:
			    0) '2k Block'
			    1) '4k Block'
			    2) '8k Block'
			    3) '16k Block'
			Oid=1.3.6.1.4.1.31968.3.1.4.2.2.3.11
			"
	::= { txNotifObjects 11 }

txRemoteAcmEsn0AlarmInfo OBJECT-TYPE
	SYNTAX		INTEGER {
		remoteAcmEsN0Ok(0),
		remoteAcmLowEsN0Alarm(1)
	}
	MAX-ACCESS	accessible-for-notify
	STATUS		current
	DESCRIPTION "Tx ACM Remote Low Es/N0 Alarm, where:
			    0) 'Remote ACM Es/N0 Ok'
			    1) 'REMOTE ACM LOW ES/N0 ALARM'
			Oid=1.3.6.1.4.1.31968.3.1.4.2.2.3.12
			"
	::= { txNotifObjects 12 }

txRemoteAcmEsn0Info OBJECT-TYPE
	SYNTAX		Integer32
	UNITS		"0.01 dB"
	MAX-ACCESS	accessible-for-notify
	STATUS		current
	DESCRIPTION "Tx ACM Remote Es/N0
			Oid=1.3.6.1.4.1.31968.3.1.4.2.2.3.13
			"
	::= { txNotifObjects 13 }

txDataAlarmInfo OBJECT-TYPE
	SYNTAX		INTEGER {
		dataOk(0),
		dataInactivityAlarm(1)
	}
	MAX-ACCESS	accessible-for-notify
	STATUS		current
	DESCRIPTION "Tx Data Activity Alarm, where:
			    0) 'Data Ok'
			    1) 'DATA INACTIVITY ALARM'
			Oid=1.3.6.1.4.1.31968.3.1.4.2.2.3.14
			"
	::= { txNotifObjects 14 }

txTemperatureAlarmInfo OBJECT-TYPE
	SYNTAX		INTEGER {
		temperatureOk(0),
		overTemperatureAlarm(1)
	}
	MAX-ACCESS	accessible-for-notify
	STATUS		current
	DESCRIPTION "Tx Temperature Alarm, where:
			    0) 'Temperature Ok'
			    1) 'OVER TEMPERATURE ALARM'
			Oid=1.3.6.1.4.1.31968.3.1.4.2.2.3.15
			"
	::= { txNotifObjects 15 }

txRfTemperatureInfo OBJECT-TYPE
	SYNTAX		Integer32
	UNITS		"0.1 Degree C"
	MAX-ACCESS	accessible-for-notify
	STATUS		current
	DESCRIPTION "Tx RF Temperature
			Oid=1.3.6.1.4.1.31968.3.1.4.2.2.3.16
			"
	::= { txNotifObjects 16 }

txFpga1TemperatureInfo OBJECT-TYPE
	SYNTAX		Integer32
	UNITS		"0.1 Degree C"
	MAX-ACCESS	accessible-for-notify
	STATUS		current
	DESCRIPTION "Tx FPGA 1 Temperature
			Oid=1.3.6.1.4.1.31968.3.1.4.2.2.3.17
			"
	::= { txNotifObjects 17 }

txHardwareAlarmInfo OBJECT-TYPE
	SYNTAX		INTEGER {
		hardwareAlarmOk(0),
		hardwareAlarm(1)
	}
	MAX-ACCESS	accessible-for-notify
	STATUS		current
	DESCRIPTION "Tx Hardware Alarm, where:
			    0) 'Hardware Alarm Ok'
			    1) 'HARDWARE ALARM'
			Oid=1.3.6.1.4.1.31968.3.1.4.2.2.3.18
			"
	::= { txNotifObjects 18 }

txHardwareAlarmBitsInfo OBJECT-TYPE
	SYNTAX		BITS {
		vint1(0),
		vaux1(1),
		clock1(2),
		n100mhz(3),
		n122mhz(4),
		lo(5),
		level(6),
		memory1(7),
		cxr(8),
		encoder(9),
		invalidKey(10),
		temperature(11)
	}
	MAX-ACCESS	accessible-for-notify
	STATUS		current
	DESCRIPTION "Tx Binary Hardware Alarms, where:
			    0) 'VInt1'
			    1) 'VAux1'
			    2) 'Clock1'
			    3) '100MHz'
			    4) '122MHz'
			    5) 'LO'
			    6) 'Level'
			    7) 'Memory1'
			    8) 'Cxr'
			    9) 'Encoder'
			    10) 'Invalid Key'
			    11) 'Temperature'
			Oid=1.3.6.1.4.1.31968.3.1.4.2.2.3.19
			"
	::= { txNotifObjects 19 }

txVcmMccChannelAlarmInfo OBJECT-TYPE
	SYNTAX		INTEGER {
		queueRemoteChannelOk(0),
		queueRemoteChannelAlarm(1)
	}
	MAX-ACCESS	accessible-for-notify
	STATUS		current
	DESCRIPTION "Tx VCM MCC Channel Alarm, where:
			    0) 'Queue Remote Channel Ok'
			    1) 'QUEUE REMOTE CHANNEL ALARM'
			Oid=1.3.6.1.4.1.31968.3.1.4.2.2.3.20
			"
	::= { txNotifObjects 20 }

txVcmLowEsn0AlarmInfo OBJECT-TYPE
	SYNTAX		INTEGER {
		queueEsN0Ok(0),
		queueLowEsN0Alarm(1)
	}
	MAX-ACCESS	accessible-for-notify
	STATUS		current
	DESCRIPTION "Tx VCM Low Es/N0 Alarm, where:
			    0) 'Queue Es/N0 Ok'
			    1) 'QUEUE LOW Es/N0 ALARM'
			Oid=1.3.6.1.4.1.31968.3.1.4.2.2.3.21
			"
	::= { txNotifObjects 21 }

txVcmMinModcodAlarmInfo OBJECT-TYPE
	SYNTAX		INTEGER {
		queueModcodOk(0),
		queueMinimumModcodAlarm(1)
	}
	MAX-ACCESS	accessible-for-notify
	STATUS		current
	DESCRIPTION "Tx VCM Minimum ModCod Alarm, where:
			    0) 'Queue ModCod Ok'
			    1) 'QUEUE MINIMUM MODCOD ALARM'
			Oid=1.3.6.1.4.1.31968.3.1.4.2.2.3.22
			"
	::= { txNotifObjects 22 }

txVcmCirMaxAlarmInfo OBJECT-TYPE
	SYNTAX		INTEGER {
		dataOk(0),
		dataInactivityAlarm(1)
	}
	MAX-ACCESS	accessible-for-notify
	STATUS		current
	DESCRIPTION "Tx VCM CIR Maximum Limit Alarm, where:
			    0) 'Data Ok'
			    1) 'DATA INACTIVITY ALARM'
			Oid=1.3.6.1.4.1.31968.3.1.4.2.2.3.23
			"
	::= { txNotifObjects 23 }

txVcmDataAlarmInfo OBJECT-TYPE
	SYNTAX		INTEGER {
		dataOk(0),
		dataInactivityAlarm(1)
	}
	MAX-ACCESS	accessible-for-notify
	STATUS		current
	DESCRIPTION "Tx VCM Data Activity Alarm, where:
			    0) 'Data Ok'
			    1) 'DATA INACTIVITY ALARM'
			Oid=1.3.6.1.4.1.31968.3.1.4.2.2.3.24
			"
	::= { txNotifObjects 24 }

m7xcObjectNotifGroups	OBJECT IDENTIFIER ::= { m7xcModemNotifications 3 }

m7xcObjectNotifGroup OBJECT-GROUP
	OBJECTS {
		eventCountInfo,
		unitStartupInfo,
		unitStartupConfigInfo,
		unitFpgaLoadAlarmInfo,
		unitFileLoadAlarmInfo,
		unitEepromLoadAlarmInfo,
		unitUncalibratedAlarmInfo,
		unitFactoryDefaultInfo,
		unitFirmwareUpdateInfo,
		unitHardwareAlarmInfo,
		unitShutdownAlarmInfo,
		unitCpuTemperatureAlarmInfo,
		unitCpuTemperatureInfo,
		unitReferenceInfo,
		unitMgmtPortLinkInfo,
		unitDataPortLinkInfo,
		unitInputPowerAlarmInfo,
		unitInputPowerVoltageInfo,
		unitTestAlarmInfo,
		unitMonitorAlarmInfo,
		unitMonitorVoltageInfo,
		unitAuthenticationFailInfo,
		unitAccessIpInfo,
		unitAccessIpAddressInfo,
		unitAccessPortInfo,
		unitAccessPortAddressInfo,
		unitTamperAlarmInfo,
		unitTrialAlarmInfo,
		unitDhcpAcquiredIpAddressInfo,
		unitDateTimeInfo,
		unitConfigChangedInfo,
		unitConfigStoredInfo,
		unitConfigRestoredInfo,
		unitRtcBatteryAlarmInfo,
		unitRtcBatteryVoltageInfo,
		unitAcuInfo,
		txChannelInfo,
		txWaveformInfo,
		txRfCxrInfo,
		txOutputInfo,
		txCxrMuteInfo,
		txAupcAlarmInfo,
		txRemoteChannelAlarmInfo,
		txTransecInfo,
		txModcodDvbInfo,
		txModcodLdpcGen2Info,
		txModcodLdpcGen2BlockSizeInfo,
		txRemoteAcmEsn0AlarmInfo,
		txRemoteAcmEsn0Info,
		txDataAlarmInfo,
		txTemperatureAlarmInfo,
		txRfTemperatureInfo,
		txFpga1TemperatureInfo,
		txHardwareAlarmInfo,
		txHardwareAlarmBitsInfo,
		txVcmMccChannelAlarmInfo,
		txVcmLowEsn0AlarmInfo,
		txVcmMinModcodAlarmInfo,
		txVcmCirMaxAlarmInfo,
		txVcmDataAlarmInfo,
		rxChannelInfo,
		rxWaveformInfo,
		rxEchoLockAlarmInfo,
		rxEchoLevelAlarmInfo,
		rxEchoLevelImbalanceInfo,
		rxEchoOffsetAlarmInfo,
		rxEchoOffsetImbalanceInfo,
		rxLockInfo,
		rxLowMarginAlarmInfo,
		rxLowMarginInfo,
		rxLowLevelAlarmInfo,
		rxLowLevelInfo,
		rxMaxAgcAlarmInfo,
		rxLnbPowerAlarmInfo,
		rxLnbPowerVoltageInfo,
		rxLnbPowerCurrentInfo,
		rxTransecInfo,
		rxModcodDvbInfo,
		rxModcodLdpcGen2Info,
		rxModcodLdpcGen2BlockSizeInfo,
		rxAcmLowAlarmInfo,
		rxAcmLowEsn0Info,
		rxDataAlarmInfo,
		rxDataConfigurationMismatchInfo,
		rxTemperatureAlarmInfo,
		rxRfTemperatureInfo,
		rxFpga2TemperatureInfo,
		rxFpga3TemperatureInfo,
		rxHardwareAlarmInfo,
		rxHardwareAlarmBitsInfo,
		rxDataPortLinkRateAlarmInfo,
		rxAcmTxHubAlarmInfo
	}
	STATUS		current
	DESCRIPTION	"Description"
	::= { m7xcObjectNotifGroups 1 }

unitStartupNotif NOTIFICATION-TYPE
	OBJECTS {
		unitStartupInfo,
		unitStartupConfigInfo
	}
	STATUS		current
	DESCRIPTION "Unit Startup Notification
			Oid=1.3.6.1.4.1.31968.3.1.4.2.4.1.0.1
			"
	::= { unitNotifs 1 }

unitFpgaLoadAlarmNotif NOTIFICATION-TYPE
	OBJECTS {
		eventCountInfo,
		unitFpgaLoadAlarmInfo
	}
	STATUS		current
	DESCRIPTION "Unit FPGA Load Alarm Notification
			Oid=1.3.6.1.4.1.31968.3.1.4.2.4.1.0.2
			"
	::= { unitNotifs 2 }

unitFileLoadAlarmNotif NOTIFICATION-TYPE
	OBJECTS {
		eventCountInfo,
		unitFileLoadAlarmInfo
	}
	STATUS		current
	DESCRIPTION "Unit File Load Alarm Notification
			Oid=1.3.6.1.4.1.31968.3.1.4.2.4.1.0.3
			"
	::= { unitNotifs 3 }

unitEepromLoadAlarmNotif NOTIFICATION-TYPE
	OBJECTS {
		eventCountInfo,
		unitEepromLoadAlarmInfo
	}
	STATUS		current
	DESCRIPTION "Unit EEPROM Load Alarm Notification
			Oid=1.3.6.1.4.1.31968.3.1.4.2.4.1.0.4
			"
	::= { unitNotifs 4 }

unitUncalibratedAlarmNotif NOTIFICATION-TYPE
	OBJECTS {
		unitUncalibratedAlarmInfo
	}
	STATUS		current
	DESCRIPTION "Unit Calibration Load Alarm Notification
			Oid=1.3.6.1.4.1.31968.3.1.4.2.4.1.0.5
			"
	::= { unitNotifs 5 }

unitFactoryDefaultNotif NOTIFICATION-TYPE
	OBJECTS {
		unitFactoryDefaultInfo
	}
	STATUS		current
	DESCRIPTION "Unit Factory Default Notification
			Oid=1.3.6.1.4.1.31968.3.1.4.2.4.1.0.6
			"
	::= { unitNotifs 6 }

unitFirmwareUpdateNotif NOTIFICATION-TYPE
	OBJECTS {
		eventCountInfo,
		unitFirmwareUpdateInfo
	}
	STATUS		current
	DESCRIPTION "Unit Firmware Update Notification
			Oid=1.3.6.1.4.1.31968.3.1.4.2.4.1.0.7
			"
	::= { unitNotifs 7 }

unitHardwareAlarmNotif NOTIFICATION-TYPE
	OBJECTS {
		eventCountInfo,
		unitHardwareAlarmInfo
	}
	STATUS		current
	DESCRIPTION "Unit Hardware Alarm Notification
			Oid=1.3.6.1.4.1.31968.3.1.4.2.4.1.0.8
			"
	::= { unitNotifs 8 }

unitShutdownAlarmNotif NOTIFICATION-TYPE
	OBJECTS {
		eventCountInfo,
		unitShutdownAlarmInfo
	}
	STATUS		current
	DESCRIPTION "Unit Over Temperature Shutdown Alarm Notification
			Oid=1.3.6.1.4.1.31968.3.1.4.2.4.1.0.9
			"
	::= { unitNotifs 9 }

unitCpuTemperatureAlarmNotif NOTIFICATION-TYPE
	OBJECTS {
		eventCountInfo,
		unitCpuTemperatureAlarmInfo,
		unitCpuTemperatureInfo
	}
	STATUS		current
	DESCRIPTION "Unit CPU Over Temperature Alarm Notification
			Oid=1.3.6.1.4.1.31968.3.1.4.2.4.1.0.10
			"
	::= { unitNotifs 10 }

unitReferenceNotif NOTIFICATION-TYPE
	OBJECTS {
		eventCountInfo,
		unitReferenceInfo
	}
	STATUS		current
	DESCRIPTION "Unit Reference Notification
			Oid=1.3.6.1.4.1.31968.3.1.4.2.4.1.0.11
			"
	::= { unitNotifs 11 }

unitMgmtPortLinkNotif NOTIFICATION-TYPE
	OBJECTS {
		eventCountInfo,
		unitMgmtPortLinkInfo
	}
	STATUS		current
	DESCRIPTION "Unit Mgmt Port Link Notification
			Oid=1.3.6.1.4.1.31968.3.1.4.2.4.1.0.12
			"
	::= { unitNotifs 12 }

unitDataPortLinkNotif NOTIFICATION-TYPE
	OBJECTS {
		eventCountInfo,
		unitDataPortLinkInfo
	}
	STATUS		current
	DESCRIPTION "Unit Data Port Notification
			Oid=1.3.6.1.4.1.31968.3.1.4.2.4.1.0.13
			"
	::= { unitNotifs 13 }

unitInputPowerAlarmNotif NOTIFICATION-TYPE
	OBJECTS {
		eventCountInfo,
		unitInputPowerAlarmInfo,
		unitInputPowerVoltageInfo
	}
	STATUS		current
	DESCRIPTION "Unit Input Power Alarm Notification
			Oid=1.3.6.1.4.1.31968.3.1.4.2.4.1.0.14
			"
	::= { unitNotifs 14 }

unitTestAlarmNotif NOTIFICATION-TYPE
	OBJECTS {
		eventCountInfo,
		unitTestAlarmInfo
	}
	STATUS		current
	DESCRIPTION "Unit Test Active Alarm Notification
			Oid=1.3.6.1.4.1.31968.3.1.4.2.4.1.0.15
			"
	::= { unitNotifs 15 }

unitMonitorAlarmNotif NOTIFICATION-TYPE
	OBJECTS {
		eventCountInfo,
		unitMonitorAlarmInfo,
		unitMonitorVoltageInfo
	}
	STATUS		current
	DESCRIPTION "Unit Monitor Input Alarm Notification
			Oid=1.3.6.1.4.1.31968.3.1.4.2.4.1.0.16
			"
	::= { unitNotifs 16 }

unitAuthenticationFailNotif NOTIFICATION-TYPE
	OBJECTS {
		eventCountInfo,
		unitAuthenticationFailInfo
	}
	STATUS		current
	DESCRIPTION "Unit Authentication Failure Notification
			Oid=1.3.6.1.4.1.31968.3.1.4.2.4.1.0.17
			"
	::= { unitNotifs 17 }

unitAccessIpNotif NOTIFICATION-TYPE
	OBJECTS {
		eventCountInfo,
		unitAccessIpInfo,
		unitAccessIpAddressInfo
	}
	STATUS		current
	DESCRIPTION "Unit IP Access Notification
			Oid=1.3.6.1.4.1.31968.3.1.4.2.4.1.0.18
			"
	::= { unitNotifs 18 }

unitAccessPortNotif NOTIFICATION-TYPE
	OBJECTS {
		eventCountInfo,
		unitAccessPortInfo,
		unitAccessPortAddressInfo
	}
	STATUS		current
	DESCRIPTION "Unit Port Access Notification
			Oid=1.3.6.1.4.1.31968.3.1.4.2.4.1.0.19
			"
	::= { unitNotifs 19 }

unitTamperAlarmNotif NOTIFICATION-TYPE
	OBJECTS {
		eventCountInfo,
		unitTamperAlarmInfo
	}
	STATUS		current
	DESCRIPTION "Unit Tamper Alarm Notification
			Oid=1.3.6.1.4.1.31968.3.1.4.2.4.1.0.20
			"
	::= { unitNotifs 20 }

unitTrialAlarmNotif NOTIFICATION-TYPE
	OBJECTS {
		eventCountInfo,
		unitTrialAlarmInfo
	}
	STATUS		current
	DESCRIPTION "Unit Trial Activation Notification
			Oid=1.3.6.1.4.1.31968.3.1.4.2.4.1.0.21
			"
	::= { unitNotifs 21 }

unitDhcpAcquiredIpAddressNotif NOTIFICATION-TYPE
	OBJECTS {
		eventCountInfo,
		unitDhcpAcquiredIpAddressInfo
	}
	STATUS		current
	DESCRIPTION "Unit DHCP Acquired IP Address Notification
			Oid=1.3.6.1.4.1.31968.3.1.4.2.4.1.0.22
			"
	::= { unitNotifs 22 }

unitDateTimeNotif NOTIFICATION-TYPE
	OBJECTS {
		eventCountInfo,
		unitDateTimeInfo
	}
	STATUS		current
	DESCRIPTION "Unit Date/Time Notification
			Oid=1.3.6.1.4.1.31968.3.1.4.2.4.1.0.23
			"
	::= { unitNotifs 23 }

unitConfigChangedNotif NOTIFICATION-TYPE
	OBJECTS {
		eventCountInfo,
		unitConfigChangedInfo
	}
	STATUS		current
	DESCRIPTION "Unit Configuration Changed Notification
			Oid=1.3.6.1.4.1.31968.3.1.4.2.4.1.0.24
			"
	::= { unitNotifs 24 }

unitConfigStoredNotif NOTIFICATION-TYPE
	OBJECTS {
		eventCountInfo,
		unitConfigStoredInfo
	}
	STATUS		current
	DESCRIPTION "Unit Configuration Stored Notification
			Oid=1.3.6.1.4.1.31968.3.1.4.2.4.1.0.25
			"
	::= { unitNotifs 25 }

unitConfigRestoredNotif NOTIFICATION-TYPE
	OBJECTS {
		eventCountInfo,
		unitConfigRestoredInfo
	}
	STATUS		current
	DESCRIPTION "Unit Configuration Restored Notification
			Oid=1.3.6.1.4.1.31968.3.1.4.2.4.1.0.26
			"
	::= { unitNotifs 26 }

unitRtcBatteryAlarmNotif NOTIFICATION-TYPE
	OBJECTS {
		eventCountInfo,
		unitRtcBatteryAlarmInfo,
		unitRtcBatteryVoltageInfo
	}
	STATUS		current
	DESCRIPTION "Unit RTC Battery Alarm Notification
			Oid=1.3.6.1.4.1.31968.3.1.4.2.4.1.0.27
			"
	::= { unitNotifs 27 }

unitAcuNotif NOTIFICATION-TYPE
	OBJECTS {
		eventCountInfo,
		unitAcuInfo
	}
	STATUS		current
	DESCRIPTION "Unit ACU Notification
			Oid=1.3.6.1.4.1.31968.3.1.4.2.4.1.0.28
			"
	::= { unitNotifs 28 }

rxWaveformNotif NOTIFICATION-TYPE
	OBJECTS {
		eventCountInfo,
		rxWaveformInfo
	}
	STATUS		current
	DESCRIPTION "Rx Waveform Notification
			Oid=1.3.6.1.4.1.31968.3.1.4.2.4.2.0.1
			"
	::= { rxNotifs 1 }

rxEchoLockAlarmNotif NOTIFICATION-TYPE
	OBJECTS {
		eventCountInfo,
		rxEchoLockAlarmInfo
	}
	STATUS		current
	DESCRIPTION "Rx Echo Lock Alarm Notification
			Oid=1.3.6.1.4.1.31968.3.1.4.2.4.2.0.2
			"
	::= { rxNotifs 2 }

rxEchoLevelAlarmNotif NOTIFICATION-TYPE
	OBJECTS {
		eventCountInfo,
		rxEchoLevelAlarmInfo,
		rxEchoLevelImbalanceInfo
	}
	STATUS		current
	DESCRIPTION "Rx Echo Level Imbalance Alarm Notification
			Oid=1.3.6.1.4.1.31968.3.1.4.2.4.2.0.3
			"
	::= { rxNotifs 3 }

rxEchoOffsetAlarmNotif NOTIFICATION-TYPE
	OBJECTS {
		eventCountInfo,
		rxEchoOffsetAlarmInfo,
		rxEchoOffsetImbalanceInfo
	}
	STATUS		current
	DESCRIPTION "Rx Echo Frequency Offset Imbalance Alarm Notification
			Oid=1.3.6.1.4.1.31968.3.1.4.2.4.2.0.4
			"
	::= { rxNotifs 4 }

rxLockNotif NOTIFICATION-TYPE
	OBJECTS {
		eventCountInfo,
		rxChannelInfo,
		rxLockInfo
	}
	STATUS		current
	DESCRIPTION "Rx Lock Notification
			Oid=1.3.6.1.4.1.31968.3.1.4.2.4.2.0.5
			"
	::= { rxNotifs 5 }

rxLowMarginAlarmNotif NOTIFICATION-TYPE
	OBJECTS {
		eventCountInfo,
		rxChannelInfo,
		rxLowMarginAlarmInfo,
		rxLowMarginInfo
	}
	STATUS		current
	DESCRIPTION "Rx Low Es/N0 Margin Alarm Notification
			Oid=1.3.6.1.4.1.31968.3.1.4.2.4.2.0.6
			"
	::= { rxNotifs 6 }

rxLowLevelAlarmNotif NOTIFICATION-TYPE
	OBJECTS {
		eventCountInfo,
		rxChannelInfo,
		rxLowLevelAlarmInfo,
		rxLowLevelInfo
	}
	STATUS		current
	DESCRIPTION "Rx Low Level Alarm Notification
			Oid=1.3.6.1.4.1.31968.3.1.4.2.4.2.0.7
			"
	::= { rxNotifs 7 }

rxMaxAgcAlarmNotif NOTIFICATION-TYPE
	OBJECTS {
		eventCountInfo,
		rxMaxAgcAlarmInfo
	}
	STATUS		current
	DESCRIPTION "Rx Input Maximum AGC Overload Alarm Notification
			Oid=1.3.6.1.4.1.31968.3.1.4.2.4.2.0.8
			"
	::= { rxNotifs 8 }

rxLnbPowerAlarmNotif NOTIFICATION-TYPE
	OBJECTS {
		eventCountInfo,
		rxLnbPowerAlarmInfo,
		rxLnbPowerVoltageInfo,
		rxLnbPowerCurrentInfo
	}
	STATUS		current
	DESCRIPTION "Rx LNB Power Alarm Notification
			Oid=1.3.6.1.4.1.31968.3.1.4.2.4.2.0.9
			"
	::= { rxNotifs 9 }

rxTransecNotif NOTIFICATION-TYPE
	OBJECTS {
		eventCountInfo,
		rxChannelInfo,
		rxTransecInfo
	}
	STATUS		current
	DESCRIPTION "Rx TRANSEC Notification
			Oid=1.3.6.1.4.1.31968.3.1.4.2.4.2.0.10
			"
	::= { rxNotifs 10 }

rxModcodDvbNotif NOTIFICATION-TYPE
	OBJECTS {
		eventCountInfo,
		rxChannelInfo,
		rxModcodDvbInfo
	}
	STATUS		current
	DESCRIPTION "Rx DVB-S2X ModCod Notification
			Oid=1.3.6.1.4.1.31968.3.1.4.2.4.2.0.11
			"
	::= { rxNotifs 11 }

rxModcodLdpcGen2Notif NOTIFICATION-TYPE
	OBJECTS {
		eventCountInfo,
		rxChannelInfo,
		rxModcodLdpcGen2Info,
		rxModcodLdpcGen2BlockSizeInfo
	}
	STATUS		current
	DESCRIPTION "Rx LDPC-Gen2 ModCod Notification
			Oid=1.3.6.1.4.1.31968.3.1.4.2.4.2.0.12
			"
	::= { rxNotifs 12 }

rxAcmLowAlarmNotif NOTIFICATION-TYPE
	OBJECTS {
		eventCountInfo,
		rxChannelInfo,
		rxAcmLowAlarmInfo,
		rxAcmLowEsn0Info
	}
	STATUS		current
	DESCRIPTION "Rx ACM Low Es/N0 Alarm Notification
			Oid=1.3.6.1.4.1.31968.3.1.4.2.4.2.0.13
			"
	::= { rxNotifs 13 }

rxDataAlarmNotif NOTIFICATION-TYPE
	OBJECTS {
		eventCountInfo,
		rxChannelInfo,
		rxDataAlarmInfo
	}
	STATUS		current
	DESCRIPTION "Rx Data Activity Alarm Notification
			Oid=1.3.6.1.4.1.31968.3.1.4.2.4.2.0.14
			"
	::= { rxNotifs 14 }

rxDataConfigurationMismatchNotif NOTIFICATION-TYPE
	OBJECTS {
		eventCountInfo,
		rxChannelInfo,
		rxDataConfigurationMismatchInfo
	}
	STATUS		current
	DESCRIPTION "Rx Rx/Tx Configuratin Mismatch Notification
			Oid=1.3.6.1.4.1.31968.3.1.4.2.4.2.0.15
			"
	::= { rxNotifs 15 }

rxTemperatureAlarmNotif NOTIFICATION-TYPE
	OBJECTS {
		eventCountInfo,
		rxTemperatureAlarmInfo,
		rxRfTemperatureInfo,
		rxFpga2TemperatureInfo,
		rxFpga3TemperatureInfo
	}
	STATUS		current
	DESCRIPTION "Rx Temperature Alarm Notification
			Oid=1.3.6.1.4.1.31968.3.1.4.2.4.2.0.16
			"
	::= { rxNotifs 16 }

rxHardwareAlarmNotif NOTIFICATION-TYPE
	OBJECTS {
		eventCountInfo,
		rxHardwareAlarmInfo,
		rxHardwareAlarmBitsInfo
	}
	STATUS		current
	DESCRIPTION "Rx Hardware Alarm Notification
			Oid=1.3.6.1.4.1.31968.3.1.4.2.4.2.0.17
			"
	::= { rxNotifs 17 }

rxDataPortLinkRateAlarmNotif NOTIFICATION-TYPE
	OBJECTS {
		eventCountInfo,
		rxDataPortLinkRateAlarmInfo
	}
	STATUS		current
	DESCRIPTION "Rx Data Port Link Rate Alarm Notification
			Oid=1.3.6.1.4.1.31968.3.1.4.2.4.2.0.18
			"
	::= { rxNotifs 18 }

rxAcmTxHubAlarmNotif NOTIFICATION-TYPE
	OBJECTS {
		eventCountInfo,
		rxAcmTxHubAlarmInfo
	}
	STATUS		current
	DESCRIPTION "Rx ACM Tx Hub Alarm Notification
			Oid=1.3.6.1.4.1.31968.3.1.4.2.4.2.0.19
			"
	::= { rxNotifs 19 }

txWaveformNotif NOTIFICATION-TYPE
	OBJECTS {
		eventCountInfo,
		txWaveformInfo
	}
	STATUS		current
	DESCRIPTION "Tx Waveform Notification
			Oid=1.3.6.1.4.1.31968.3.1.4.2.4.3.0.1
			"
	::= { txNotifs 1 }

txRfCxrNotif NOTIFICATION-TYPE
	OBJECTS {
		eventCountInfo,
		txRfCxrInfo
	}
	STATUS		current
	DESCRIPTION "Tx RF Master Output Notification
			Oid=1.3.6.1.4.1.31968.3.1.4.2.4.3.0.2
			"
	::= { txNotifs 2 }

txOutputNotif NOTIFICATION-TYPE
	OBJECTS {
		eventCountInfo,
		txChannelInfo,
		txOutputInfo
	}
	STATUS		current
	DESCRIPTION "Tx Output Notification
			Oid=1.3.6.1.4.1.31968.3.1.4.2.4.3.0.3
			"
	::= { txNotifs 3 }

txCxrMuteNotif NOTIFICATION-TYPE
	OBJECTS {
		eventCountInfo,
		txCxrMuteInfo
	}
	STATUS		current
	DESCRIPTION "Tx Carrier Mute Notification
			Oid=1.3.6.1.4.1.31968.3.1.4.2.4.3.0.4
			"
	::= { txNotifs 4 }

txAupcAlarmNotif NOTIFICATION-TYPE
	OBJECTS {
		eventCountInfo,
		txAupcAlarmInfo
	}
	STATUS		current
	DESCRIPTION "Tx AUPC Alarm Notification
			Oid=1.3.6.1.4.1.31968.3.1.4.2.4.3.0.5
			"
	::= { txNotifs 5 }

txRemoteChannelAlarmNotif NOTIFICATION-TYPE
	OBJECTS {
		eventCountInfo,
		txRemoteChannelAlarmInfo
	}
	STATUS		current
	DESCRIPTION "Tx Remote Channel Alarm Notification
			Oid=1.3.6.1.4.1.31968.3.1.4.2.4.3.0.6
			"
	::= { txNotifs 6 }

txTransecNotif NOTIFICATION-TYPE
	OBJECTS {
		eventCountInfo,
		txTransecInfo
	}
	STATUS		current
	DESCRIPTION "Tx TRANSEC Notification
			Oid=1.3.6.1.4.1.31968.3.1.4.2.4.3.0.7
			"
	::= { txNotifs 7 }

txModcodDvbNotif NOTIFICATION-TYPE
	OBJECTS {
		eventCountInfo,
		txModcodDvbInfo
	}
	STATUS		current
	DESCRIPTION "Tx DVB-S2X ModCod Notification
			Oid=1.3.6.1.4.1.31968.3.1.4.2.4.3.0.8
			"
	::= { txNotifs 8 }

txModcodLdpcGen2Notif NOTIFICATION-TYPE
	OBJECTS {
		eventCountInfo,
		txModcodLdpcGen2Info,
		txModcodLdpcGen2BlockSizeInfo
	}
	STATUS		current
	DESCRIPTION "Tx LDPC-Gen2 ModCod Notification
			Oid=1.3.6.1.4.1.31968.3.1.4.2.4.3.0.9
			"
	::= { txNotifs 9 }

txRemoteAcmEsn0AlarmNotif NOTIFICATION-TYPE
	OBJECTS {
		eventCountInfo,
		txRemoteAcmEsn0AlarmInfo,
		txRemoteAcmEsn0Info
	}
	STATUS		current
	DESCRIPTION "Tx ACM Remote Low Es/N0 Alarm Notification
			Oid=1.3.6.1.4.1.31968.3.1.4.2.4.3.0.10
			"
	::= { txNotifs 10 }

txDataAlarmNotif NOTIFICATION-TYPE
	OBJECTS {
		eventCountInfo,
		txDataAlarmInfo
	}
	STATUS		current
	DESCRIPTION "Tx Data Activity Alarm Notification
			Oid=1.3.6.1.4.1.31968.3.1.4.2.4.3.0.11
			"
	::= { txNotifs 11 }

txTemperatureAlarmNotif NOTIFICATION-TYPE
	OBJECTS {
		eventCountInfo,
		txTemperatureAlarmInfo,
		txRfTemperatureInfo,
		txFpga1TemperatureInfo
	}
	STATUS		current
	DESCRIPTION "Tx Temperature Alarm Notification
			Oid=1.3.6.1.4.1.31968.3.1.4.2.4.3.0.12
			"
	::= { txNotifs 12 }

txHardwareAlarmNotif NOTIFICATION-TYPE
	OBJECTS {
		eventCountInfo,
		txHardwareAlarmInfo,
		txHardwareAlarmBitsInfo
	}
	STATUS		current
	DESCRIPTION "Tx Hardware Alarm Notification
			Oid=1.3.6.1.4.1.31968.3.1.4.2.4.3.0.13
			"
	::= { txNotifs 13 }

txVcmMccChannelAlarmNotif NOTIFICATION-TYPE
	OBJECTS {
		eventCountInfo,
		txChannelInfo,
		txVcmMccChannelAlarmInfo
	}
	STATUS		current
	DESCRIPTION "Tx VCM MCC Channel Alarm Notification
			Oid=1.3.6.1.4.1.31968.3.1.4.2.4.3.0.14
			"
	::= { txNotifs 14 }

txVcmLowEsn0AlarmNotif NOTIFICATION-TYPE
	OBJECTS {
		eventCountInfo,
		txChannelInfo,
		txVcmLowEsn0AlarmInfo
	}
	STATUS		current
	DESCRIPTION "Tx VCM Low Es/N0 Alarm Notification
			Oid=1.3.6.1.4.1.31968.3.1.4.2.4.3.0.15
			"
	::= { txNotifs 15 }

txVcmMinModcodAlarmNotif NOTIFICATION-TYPE
	OBJECTS {
		eventCountInfo,
		txChannelInfo,
		txVcmMinModcodAlarmInfo
	}
	STATUS		current
	DESCRIPTION "Tx VCM Minimum ModCod Alarm Notification
			Oid=1.3.6.1.4.1.31968.3.1.4.2.4.3.0.16
			"
	::= { txNotifs 16 }

txVcmCirMaxAlarmNotif NOTIFICATION-TYPE
	OBJECTS {
		eventCountInfo,
		txVcmCirMaxAlarmInfo
	}
	STATUS		current
	DESCRIPTION "Tx VCM CIR Maximum Limit Alarm Notification
			Oid=1.3.6.1.4.1.31968.3.1.4.2.4.3.0.17
			"
	::= { txNotifs 17 }

txVcmDataAlarmNotif NOTIFICATION-TYPE
	OBJECTS {
		eventCountInfo,
		txChannelInfo,
		txVcmDataAlarmInfo
	}
	STATUS		current
	DESCRIPTION "Tx VCM Data Activity Alarm Notification
			Oid=1.3.6.1.4.1.31968.3.1.4.2.4.3.0.18
			"
	::= { txNotifs 18 }

m7xcTrapNotifGroups		OBJECT IDENTIFIER ::= { m7xcModemNotifications 5 }

m7xcTrapNotifGroup NOTIFICATION-GROUP
	NOTIFICATIONS {
		unitStartupNotif,
		unitFpgaLoadAlarmNotif,
		unitFileLoadAlarmNotif,
		unitEepromLoadAlarmNotif,
		unitUncalibratedAlarmNotif,
		unitFactoryDefaultNotif,
		unitFirmwareUpdateNotif,
		unitHardwareAlarmNotif,
		unitShutdownAlarmNotif,
		unitCpuTemperatureAlarmNotif,
		unitReferenceNotif,
		unitMgmtPortLinkNotif,
		unitDataPortLinkNotif,
		unitInputPowerAlarmNotif,
		unitTestAlarmNotif,
		unitMonitorAlarmNotif,
		unitAuthenticationFailNotif,
		unitAccessIpNotif,
		unitAccessPortNotif,
		unitTamperAlarmNotif,
		unitTrialAlarmNotif,
		unitDhcpAcquiredIpAddressNotif,
		unitDateTimeNotif,
		unitConfigChangedNotif,
		unitConfigStoredNotif,
		unitConfigRestoredNotif,
		unitRtcBatteryAlarmNotif,
		unitAcuNotif,
		txWaveformNotif,
		txRfCxrNotif,
		txOutputNotif,
		txCxrMuteNotif,
		txAupcAlarmNotif,
		txRemoteChannelAlarmNotif,
		txTransecNotif,
		txModcodDvbNotif,
		txModcodLdpcGen2Notif,
		txRemoteAcmEsn0AlarmNotif,
		txDataAlarmNotif,
		txTemperatureAlarmNotif,
		txHardwareAlarmNotif,
		txVcmMccChannelAlarmNotif,
		txVcmLowEsn0AlarmNotif,
		txVcmMinModcodAlarmNotif,
		txVcmCirMaxAlarmNotif,
		txVcmDataAlarmNotif,
		rxWaveformNotif,
		rxEchoLockAlarmNotif,
		rxEchoLevelAlarmNotif,
		rxEchoOffsetAlarmNotif,
		rxLockNotif,
		rxLowMarginAlarmNotif,
		rxLowLevelAlarmNotif,
		rxMaxAgcAlarmNotif,
		rxLnbPowerAlarmNotif,
		rxTransecNotif,
		rxModcodDvbNotif,
		rxModcodLdpcGen2Notif,
		rxAcmLowAlarmNotif,
		rxDataAlarmNotif,
		rxDataConfigurationMismatchNotif,
		rxTemperatureAlarmNotif,
		rxHardwareAlarmNotif,
		rxDataPortLinkRateAlarmNotif,
		rxAcmTxHubAlarmNotif
	}
	STATUS		current
	DESCRIPTION	"Description"
	::= { m7xcTrapNotifGroups 1 }

END
